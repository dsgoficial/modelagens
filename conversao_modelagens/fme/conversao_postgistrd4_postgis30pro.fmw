FME workspace conversao_postgistrd4_postgis30pro.fmw

Parameters:
- direcao = ida   # Direção do mapeamento
- JsonMapeamento1 = E:\DINIZ\3_Desenvolvimento\modelagens\conversao_modelagens\arquivos_mapeamento\conversao_pg-trd-44_pg-edgv-300.json   # Arquivo de mapeamento TRD->EDGV3
- FEATURE_TYPES = mgcp.aaa010 mgcp.aaa012 mgcp.aaa052 mgcp.aab000 mgcp.aab010 mgcp.aac000 mgcp.aac030 mgcp.aad010 mgcp.aad030 mgcp.aad050 mgcp.aah050 mgcp.aai030 mgcp.aaj010 mgcp.aaj030 mgcp.aaj110 mgcp.aak030 mgcp.aak040 mgcp.aak060 mgcp.aak090 mgcp.aak100 mgcp.aak120 mgcp.aak160 mgcp.aak170 mgcp.aak180 mgcp.aak190 mgcp.aal010 mgcp.aal012 mgcp.aal015 mgcp.aal019 mgcp.aal020 mgcp.aal030 mgcp.aal060 mgcp.aal105 mgcp.aal140 mgcp.aal170 mgcp.aal200 mgcp.aal208 mgcp.aam010 mgcp.aam020 mgcp.aam030 mgcp.aam040 mgcp.aam060 mgcp.aam070 mgcp.aan060 mgcp.aan076 mgcp.aaq040 mgcp.aaq116 mgcp.aaq125 mgcp.aaq130 mgcp.aaq135 mgcp.aaq140 mgcp.aat050 mgcp.aba030 mgcp.aba040 mgcp.aba050 mgcp.abb005 mgcp.abb041 mgcp.abb043 mgcp.abb090 mgcp.abb140 mgcp.abb190 mgcp.abb240 mgcp.abd100 mgcp.abd120 mgcp.abh010 mgcp.abh015 mgcp.abh020 mgcp.abh030 mgcp.abh040 mgcp.abh050 mgcp.abh051 mgcp.abh080 mgcp.abh090 mgcp.abh120 mgcp.abh130 mgcp.abh135 mgcp.abh140 mgcp.abh150 mgcp.abh155 mgcp.abh160 mgcp.abh165 mgcp.abi020 mgcp.abi030 mgcp.abj020 mgcp.abj030 mgcp.abj031 mgcp.abj100 mgcp.abj110 mgcp.ada010 mgcp.adb061 mgcp.adb090 mgcp.adb115 mgcp.adb160 mgcp.adb170 mgcp.adb180 mgcp.adb200 mgcp.aea010 mgcp.aea040 mgcp.aea050 mgcp.aea055 mgcp.aeb010 mgcp.aeb020 mgcp.aec010 mgcp.aec020 mgcp.aec030 mgcp.aec040 mgcp.aec060 mgcp.aed010 mgcp.aed020 mgcp.aed030 mgcp.afa015 mgcp.afa100 mgcp.agb005 mgcp.agb015 mgcp.agb035 mgcp.agb045 mgcp.agb055 mgcp.agb065 mgcp.agb075 mgcp.agb230 mgcp.aquisicao_area_bloqueio_visual_a mgcp.aquisicao_area_tsi_a mgcp.aquisicao_area_vegetacao_a mgcp.aquisicao_centroide_bloqueio_visual_p mgcp.aquisicao_centroide_hidrografia_p mgcp.aquisicao_centroide_vegetacao_p mgcp.aquisicao_limite_bloqueio_visual_l mgcp.aquisicao_limite_hidrografia_l mgcp.aquisicao_limite_vegetacao_l mgcp.asu001 mgcp.aux_moldura_a mgcp.aux_objeto_desconhecido_p mgcp.aux_rascunho_a mgcp.aux_rascunho_l mgcp.azd020 mgcp.laf020 mgcp.lah025 mgcp.lak130 mgcp.lak150 mgcp.lak190 mgcp.lal060 mgcp.lal070 mgcp.lal210 mgcp.lal260 mgcp.lan010 mgcp.lan050 mgcp.lap010 mgcp.lap030 mgcp.lap050 mgcp.laq040 mgcp.laq063 mgcp.laq070 mgcp.laq075 mgcp.laq113 mgcp.laq130 mgcp.lat030 mgcp.lat041 mgcp.lat060 mgcp.lba010 mgcp.lbb041 mgcp.lbb043 mgcp.lbb140 mgcp.lbb190 mgcp.lbb230 mgcp.lbd120 mgcp.lbh010 mgcp.lbh020 mgcp.lbh030 mgcp.lbh060 mgcp.lbh070 mgcp.lbh110 mgcp.lbh120 mgcp.lbh140 mgcp.lbh165 mgcp.lbh180 mgcp.lbi020 mgcp.lbi030 mgcp.lbi040 mgcp.lbi041 mgcp.lbj031 mgcp.lbj040 mgcp.ldb010 mgcp.ldb061 mgcp.ldb070 mgcp.ldb071 mgcp.ldb090 mgcp.ldb100 mgcp.ldb110 mgcp.ldb160 mgcp.ldb200 mgcp.lea020 mgcp.lec030 mgcp.lfa090 mgcp.lgb050 mgcp.paa010 mgcp.paa012 mgcp.paa040 mgcp.paa050 mgcp.pac000 mgcp.pac020 mgcp.pac030 mgcp.pad010 mgcp.pad020 mgcp.pad030 mgcp.pad050 mgcp.paf010 mgcp.paf040 mgcp.paf070 mgcp.pah050 mgcp.pah070 mgcp.paj030 mgcp.paj050 mgcp.paj051 mgcp.paj110 mgcp.pak040 mgcp.pak150 mgcp.pak160 mgcp.pak170 mgcp.pal012 mgcp.pal015 mgcp.pal019 mgcp.pal020 mgcp.pal025 mgcp.pal030 mgcp.pal099 mgcp.pal105 mgcp.pal130 mgcp.pal210 mgcp.pal241 mgcp.pam020 mgcp.pam030 mgcp.pam040 mgcp.pam060 mgcp.pam070 mgcp.pan075 mgcp.pan076 mgcp.paq065 mgcp.paq070 mgcp.paq090 mgcp.paq110 mgcp.paq116 mgcp.paq125 mgcp.pat010 mgcp.pat042 mgcp.pat045 mgcp.pba050 mgcp.pbb155 mgcp.pbd100 mgcp.pbd110 mgcp.pbd130 mgcp.pbd180 mgcp.pbh010 mgcp.pbh070 mgcp.pbh120 mgcp.pbh145 mgcp.pbh170 mgcp.pbh180 mgcp.pbi010 mgcp.pbi020 mgcp.pbi030 mgcp.pbi040 mgcp.pbi041 mgcp.pbi050 mgcp.pbj060 mgcp.pdb029 mgcp.pdb115 mgcp.pdb150 mgcp.pdb160 mgcp.pdb180 mgcp.pec030 mgcp.pga034 mgcp.pgb030 mgcp.pgb040 mgcp.pgb050 mgcp.pgb065 mgcp.pgb220 mgcp.pgb230 mgcp.pgb485 mgcp.psu001 mgcp.pzd040 mgcp.rev_edificacao_a mgcp.rev_edificacao_l mgcp.rev_edificacao_p mgcp.rev_hidrografia_a mgcp.rev_hidrografia_l mgcp.rev_hidrografia_p mgcp.rev_transportes_a mgcp.rev_transportes_l mgcp.rev_transportes_p mgcp.rev_vegetacao_a mgcp.rev_vegetacao_l mgcp.rev_vegetacao_p mgcp.val_edificacao_a mgcp.val_edificacao_l mgcp.val_edificacao_p mgcp.val_hidrografia_a mgcp.val_hidrografia_l mgcp.val_hidrografia_p mgcp.val_transportes_a mgcp.val_transportes_l mgcp.val_transportes_p mgcp.val_vegetacao_a mgcp.val_vegetacao_l mgcp.val_vegetacao_p
- SourceDataset_POSTGIS_3 = mgcp_50k_4326_trd4   # Database
- postgis_sql_where_clause = st_intersects(geom, st_geomfromewkt('SRID=4326;MultiPolygon (((-58 -21, -58 -20, -57 -20, -57 -21, -58 -21)))'))
- DestDataset_POSTGIS_2 = sisfron_benchmark_25k_31981_edgv30pro   # Database
- SourceDataset_POSTGIS = sisfron_benchmark_25k_31981_edgv30pro   # Database
- FEATURE_TYPES_2 = edgv.aquisicao_centroide_area_construida_p edgv.aquisicao_centroide_massa_dagua_p edgv.aquisicao_centroide_vegetacao_p edgv.aquisicao_identificacao_antropizacao_a edgv.aquisicao_ilha_p edgv.aquisicao_limite_area_construida_l edgv.aquisicao_limite_massa_dagua_l edgv.aquisicao_limite_vegetacao_l edgv.aquisicao_localidade_a edgv.aux_area_nao_mapeada_a edgv.aux_insumo_externo_a edgv.aux_insumo_externo_l edgv.aux_insumo_externo_p edgv.aux_moldura_a edgv.aux_moldura_area_continua_a edgv.aux_objeto_desconhecido_a edgv.aux_objeto_desconhecido_l edgv.aux_objeto_desconhecido_p edgv.aux_reambulacao_a edgv.aux_reambulacao_l edgv.aux_reambulacao_p edgv.aux_revisao_a edgv.aux_revisao_l edgv.aux_revisao_p edgv.aux_validacao_a edgv.aux_validacao_l edgv.aux_validacao_p edgv.cobter_area_construida_a edgv.cobter_massa_dagua_a edgv.cobter_vegetacao_a edgv.constr_deposito_a edgv.constr_deposito_p edgv.constr_edificacao_a edgv.constr_edificacao_p edgv.constr_extracao_mineral_a edgv.constr_extracao_mineral_p edgv.constr_ocupacao_solo_a edgv.constr_ocupacao_solo_l edgv.constr_ocupacao_solo_p edgv.elemnat_curva_nivel_l edgv.elemnat_elemento_fisiografico_a edgv.elemnat_elemento_fisiografico_l edgv.elemnat_elemento_fisiografico_p edgv.elemnat_elemento_hidrografico_a edgv.elemnat_elemento_hidrografico_l edgv.elemnat_elemento_hidrografico_p edgv.elemnat_ilha_a edgv.elemnat_ilha_p edgv.elemnat_ponto_cotado_p edgv.elemnat_sumidouro_vertedouro_p edgv.elemnat_terreno_sujeito_inundacao_a edgv.elemnat_toponimo_fisiografico_natural_l edgv.elemnat_toponimo_fisiografico_natural_p edgv.elemnat_trecho_drenagem_l edgv.infra_alteracao_fisiografica_antropica_a edgv.infra_alteracao_fisiografica_antropica_l edgv.infra_barragem_a edgv.infra_barragem_l edgv.infra_elemento_energia_a edgv.infra_elemento_energia_l edgv.infra_elemento_energia_p edgv.infra_elemento_infraestrutura_a edgv.infra_elemento_infraestrutura_l edgv.infra_elemento_infraestrutura_p edgv.infra_elemento_viario_l edgv.infra_elemento_viario_p edgv.infra_ferrovia_l edgv.infra_mobilidade_urbana_l edgv.infra_pista_pouso_a edgv.infra_pista_pouso_l edgv.infra_pista_pouso_p edgv.infra_trecho_duto_l edgv.infra_trecho_hidroviario_l edgv.infra_vala_l edgv.infra_via_deslocamento_l edgv.llp_delimitacao_fisica_l edgv.llp_limite_especial_a edgv.llp_limite_especial_l edgv.llp_limite_legal_a edgv.llp_limite_legal_l edgv.llp_localidade_p edgv.llp_ponto_controle_p
- DestDataset_POSTGIS = sisfron_benchmark_25k_31981_edgv30pro   # Database
- JsonMapeamento2 = E:\DINIZ\3_Desenvolvimento\modelagens\conversao_modelagens\arquivos_mapeamento\conversao_pg-edgv-300-pg-edgv-300pro.json   # Arquivo de mapeamento EDGV3->EDGV3PRO

Readers:
- POSTGIS_1: POSTGIS from $(SourceDataset_POSTGIS_3)
- POSTGIS_2: POSTGIS from $(SourceDataset_POSTGIS)

Writers:
- POSTGIS_3: POSTGIS to $(DestDataset_POSTGIS_2)
- POSTGIS_4: POSTGIS to $(DestDataset_POSTGIS)

Note: trd
aaa010 (reader POSTGIS_1)
    attributes: id serial, ppo int2, nfn varchar(255), nfi varchar(255), nam varchar(255), fun int2, mzn int2, acc int2, ccn varchar(255), sdv varchar(255), sdp varchar(255), srt int2, txt varchar(255), uid varchar(255), cab int2, sdt int2, trs int2, tipo int2, wd1 float4, hwt int2, categoria varchar(255), wid float4, tos int2, mes int2, rac int2, vsp int2, obs varchar(255), rra int2, cat int2, fmm int2,
      zva float4, wtc int2, sta int2, rkf int2, mi varchar(255), rta int2, ttc int2, na2 varchar(255), ffn int2, rrc int2, vgt int2, wle int2, veg int2, boc int2, hyp int2, caa int2, cod int2, pby int2, bsc int2, pwc int2, sfs int2, fpt int2, ohb float4, rst int2, cda int2, tre int2, rgc int2, ray int2, nst int2, len float4,
      dmb float4, eet int2, tuc int2, wst int2, smc int2, wft int2, fic int2, ord int2, azc int2, iko varchar(255), ssc int2, bot int2, rel int2, bac int2, sep int2, slt int2, bloco varchar(255), crm int2, aoo float4, opc int2, afa int2, swt int2, ltn int4, fhc int2, prm int2, cns int2, rsa int2, con int2, fuc int2, frt int2,
      cct int2, scc int2, haf int2, tid int2, lfa int2, voi varchar(255), rwc int2, suc int2, rir int2, fac int2, loc int2, cra int2, dmt float4, csp int2, nos int4, gnc int2, ffp int2, gaw float4, mcc int2, wcc int2, hgt float4, corrigido int2, atc int2, ppc int2, hct int2, sdo float4
    -> Tester
Tester
    BOOL_OP = AND
    TEST_CLAUSE:
      TEST @Value(fme_feature_type) != mgcp.aquisicao_centroide_bloqueio_visual_p
      TEST @Value(fme_feature_type) != mgcp.aquisicao_centroide_hidrografia_p
      TEST @Value(fme_feature_type) != mgcp.aquisicao_centroide_vegetacao_p
      TEST @Value(fme_feature_type) != mgcp.aux_objeto_desconhecido_p
      TEST @Value(fme_feature_type) != mgcp.rev_edificacao_p
      TEST @Value(fme_feature_type) != mgcp.rev_hidrografia_p
      TEST @Value(fme_feature_type) != mgcp.rev_transportes_p
      TEST @Value(fme_feature_type) != mgcp.rev_vegetacao_p
      TEST @Value(fme_feature_type) != mgcp.val_edificacao_p
      TEST @Value(fme_feature_type) != mgcp.val_hidrografia_p
      TEST @Value(fme_feature_type) != mgcp.val_transportes_p
      TEST @Value(fme_feature_type) != mgcp.val_vegetacao_p
      TEST @Value(fme_feature_type) != mgcp.feicoes_deletadas_p
      TEST @Value(fme_feature_type) != mgcp.aquisicao_limite_bloqueio_visual_l
      TEST @Value(fme_feature_type) != mgcp.aquisicao_limite_hidrografia_l
      TEST @Value(fme_feature_type) != mgcp.aquisicao_limite_vegetacao_l
      TEST @Value(fme_feature_type) != mgcp.aux_rascunho_l
      TEST @Value(fme_feature_type) != mgcp.rev_edificacao_l
      TEST @Value(fme_feature_type) != mgcp.rev_hidrografia_l
      TEST @Value(fme_feature_type) != mgcp.rev_transportes_l
      TEST @Value(fme_feature_type) != mgcp.rev_vegetacao_l
      TEST @Value(fme_feature_type) != mgcp.val_edificacao_l
      TEST @Value(fme_feature_type) != mgcp.val_hidrografia_l
      TEST @Value(fme_feature_type) != mgcp.feicoes_deletadas_l
      TEST @Value(fme_feature_type) != mgcp.val_transportes_l
      TEST @Value(fme_feature_type) != mgcp.val_vegetacao_l
      TEST @Value(fme_feature_type) != mgcp.aux_moldura_a
      TEST @Value(fme_feature_type) != mgcp.rev_edificacao_a
      TEST @Value(fme_feature_type) != mgcp.val_hidrografia_a
      TEST @Value(fme_feature_type) != mgcp.feicoes_deletadas_a
    TEST_MODE = TEST
    PASSED -> Deaggregator
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> Reprojector
Reprojector
    DEST = EPSG:31981
    INTERPOLATION_TYPE_NAME = Nearest Neighbor
    RASTER_CELL_SIZE = Preserve Cells
    RASTER_TOLERANCE = 0.0
    SOURCE = Read from feature
    REPROJECTED -> GeometryFilter
GeometryFilter
    BREAK_AGG = No
    GEOM_PORT_NAMES = Point Line Area
    POINT -> PythonCaller_TRD_EDGV30
    LINE -> PythonCaller_TRD_EDGV30
    AREA -> PythonCaller_TRD_EDGV30
Note: mapeamento
PythonCaller_TRD_EDGV30
    NEW_ATTRIBUTES = CLASS_NOT_FOUND
    PYTHONSOURCE:
      import fme
      import fmeobjects
      import copy
      import sys
      import os
      import json

      class FeatureProcessor(object):
          def __init__(self):
              self.mappingDict = self.buildFileDict(FME_MacroValues['JsonMapeamento1'])
              self.mappingType = FME_MacroValues['direcao']

          def buildFileDict(self, mappingPath):
              file = open(mappingPath, 'r')
              data = file.read()
              mapDict = json.loads(data)
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          featDict[attr] = feature.getAttribute(attr)
                      else:
                          featDict[attr] = None
              if feature.performFunction('@GeometryType()') == 'fme_polygon' or feature.performFunction('@GeometryType()') == 'fme_donut':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              else:
                  featDict["$GEOM_TYPE"] = 'NULL'
              return featDict

          def evaluateExpression(self, featDict, expression):
              return expression["nome_atributo"] in featDict and u"{0}".format(featDict[expression["nome_atributo"]]) == u"{0}".format(expression["valor"])

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "ida":
                  key_attr_origin = "attr_ida"
                  key_attr_destiny = "attr_volta"
                  key_value_origin = "valor_ida"
                  key_value_destiny = "valor_volta"
                  key_default = "atributos_default_ida"
                  key_filter = "filtro_ida"
                  key_class_origin = "classe_ida"
                  key_class_destiny = "classe_volta"
                  key_group_origin = "tupla_ida"
                  key_group_destiny = "tupla_volta"
                  key_affix_origin = "afixo_geom_ida"
                  key_affix_destiny = "afixo_geom_volta"
                  key_schema_origin = "schema_ida"
                  key_schema_destiny = "schema_volta"
                  key_class_affix_origin = "com_afixo_geom_ida"
                  key_class_affix_destiny = "com_afixo_geom_volta"
                  key_class_schema_origin = "com_schema_ida"
                  key_class_schema_destiny = "com_schema_volta"
                  key_agregar = "agregar_geom_ida"
              else:
                  key_attr_origin = "attr_volta"
                  key_attr_destiny = "attr_ida"
                  key_value_origin = "valor_volta"
                  key_value_destiny = "valor_ida"
                  key_default = "atributos_default_volta"
                  key_filter = "filtro_volta"
                  key_class_origin = "classe_volta"
                  key_class_destiny = "classe_ida"
                  key_group_origin = "tupla_volta"
                  key_group_destiny = "tupla_ida"
                  key_affix_origin = "afixo_geom_volta"
                  key_affix_destiny = "afixo_geom_ida"
                  key_schema_origin = "schema_volta"
                  key_schema_destiny = "schema_ida"
                  key_class_affix_origin = "com_afixo_geom_volta"
                  key_class_affix_destiny = "com_afixo_geom_ida"
                  key_class_schema_origin = "com_schema_volta"
                  key_class_schema_destiny = "com_schema_ida"
                  key_agregar = "agregar_geom_volta"

              featDict["fme_feature_type_original"] = featDict["fme_feature_type"]

              if key_schema_origin in self.mappingDict and self.mappingDict[key_schema_origin]:
                  featDict["fme_feature_type"] = featDict["fme_feature_type"][len(self.mappingDict[key_schema_origin])+1:]

              featDict["fme_feature_type_sem_schema"] = featDict["fme_feature_type"]

              if key_affix_origin in self.mappingDict and 'tipo' in self.mappingDict[key_affix_origin] and self.mappingDict[key_affix_origin]['tipo'] == 'sufixo':
                  featDict["fme_feature_type"] = featDict["fme_feature_type"][:-len(self.mappingDict[key_affix_origin][featDict["$GEOM_TYPE"]])]
                  featDict["fme_feature_type_sem_afixo"] = featDict["fme_feature_type_original"][:-len(self.mappingDict[key_affix_origin][featDict["$GEOM_TYPE"]])]

              if key_affix_origin in self.mappingDict and 'tipo' in self.mappingDict[key_affix_origin] and self.mappingDict[key_affix_origin]['tipo'] == 'prefixo':
                  featDict["fme_feature_type"] = featDict["fme_feature_type"][len(self.mappingDict[key_affix_origin][featDict["$GEOM_TYPE"]]):]
                  featDict["fme_feature_type_sem_afixo"] = featDict["fme_feature_type_original"][len(self.mappingDict[key_affix_origin][featDict["$GEOM_TYPE"]]):]

              should_map = False
              for classmap in self.mappingDict['mapeamento_classes']:
                  if "sentido" not in classmap or ("sentido" in classmap and classmap["sentido"] == self.mappingType):
                      if key_class_affix_origin in classmap and classmap[key_class_affix_origin] and key_class_schema_origin in classmap and classmap[key_class_schema_origin]:
                          class_name = featDict["fme_feature_type_original"]
                      elif key_class_affix_origin in classmap and classmap[key_class_affix_origin]:
                          class_name = featDict["fme_feature_type_sem_schema"]
                      elif key_class_schema_origin in classmap and classmap[key_class_schema_origin]:
                          class_name = featDict["fme_feature_type_sem_afixo"]
                      else:
                           class_name = featDict["fme_feature_type"]

                      if classmap[key_class_origin] == class_name:
                          if key_filter in classmap:
                              if not self.evaluateFilter(featDict, classmap[key_filter]):
                                  continue
                          should_map = True
              if not should_map:
                  featDict["CLASS_NOT_FOUND"] = True
                  return featDict

              mappedFeat = copy.deepcopy(featDict)

              if key_default in self.mappingDict:
                  for default in self.mappingDict[key_default]:
                      mappedFeat[default["nome_atributo"]] = default["valor"]

              if 'mapeamento_atributos' in self.mappingDict:
                  for attmap in self.mappingDict['mapeamento_atributos']:
                      if attmap[key_attr_origin] in featDict:
                          mappedFeat[attmap[key_attr_destiny]] = featDict[attmap[key_attr_origin]]
                          if "traducao" in attmap:
                              for valuemap in attmap["traducao"]:
                                  if u"{0}".format(valuemap[key_value_origin]) == u"{0}".format(featDict[attmap[key_attr_origin]]) and ("sentido" not in valuemap or ("sentido" in valuemap and valuemap["sentido"] == self.mappingType)):
                                      mappedFeat[attmap[key_attr_destiny]] = valuemap[key_value_destiny]

              if 'mapeamento_classes' in self.mappingDict:
                  for classmap in self.mappingDict['mapeamento_classes']:
                      if "sentido" not in classmap or ("sentido" in classmap and classmap["sentido"] == self.mappingType):
                          if key_class_affix_origin in classmap and classmap[key_class_affix_origin] and key_class_schema_origin in classmap and classmap[key_class_schema_origin]:
                              class_name = featDict["fme_feature_type_original"]
                          elif key_class_affix_origin in classmap and classmap[key_class_affix_origin]:
                              class_name = featDict["fme_feature_type_sem_schema"]
                          elif key_class_schema_origin in classmap and classmap[key_class_schema_origin]:
                              class_name = featDict["fme_feature_type_sem_afixo"]
                          else:
                              class_name = featDict["fme_feature_type"]

                          if classmap[key_class_origin] == class_name:
                              if key_filter in classmap:
                                  if not self.evaluateFilter(featDict, classmap[key_filter]):
                                      continue

                              mappedFeat["fme_feature_type"] = classmap[key_class_destiny]

                              if key_class_affix_destiny in classmap and classmap[key_class_affix_destiny]:
                                  pass
                              elif key_affix_destiny in self.mappingDict and 'tipo' in self.mappingDict[key_affix_destiny]:
                                  if self.mappingDict[key_affix_destiny]['tipo'] == 'sufixo':
                                      mappedFeat["fme_feature_type"] = mappedFeat["fme_feature_type"] + self.mappingDict[key_affix_destiny][featDict["$GEOM_TYPE"]]

                                  if self.mappingDict[key_affix_destiny]['tipo'] == 'prefixo':
                                      mappedFeat["fme_feature_type"] = self.mappingDict[key_affix_destiny][featDict["$GEOM_TYPE"]] + mappedFeat["fme_feature_type"]

                              if key_class_schema_destiny in classmap and classmap[key_class_schema_destiny]:
                                  pass
                              elif key_schema_destiny in self.mappingDict and self.mappingDict[key_schema_destiny]:
                                  mappedFeat["fme_feature_type"] = self.mappingDict[key_schema_destiny] + '.' + mappedFeat["fme_feature_type"]


                              if key_default in classmap:
                                  for default in classmap[key_default]:
                                      mappedFeat[default["nome_atributo"]] = default["valor"]

                              if "mapeamento_atributos" in classmap:
                                  for attmap in classmap['mapeamento_atributos']:
                                      if attmap[key_attr_origin] in featDict:
                                          if attmap[key_attr_destiny] not in mappedFeat:
                                              mappedFeat[attmap[key_attr_destiny]] = featDict[attmap[key_attr_origin]]
                                          if "traducao" in attmap:
                                              for valuemap in attmap["traducao"]:
                                                  if u"{0}".format(valuemap[key_value_origin]) == u"{0}".format(featDict[attmap[key_attr_origin]]) and ("sentido" not in valuemap or ("sentido" in valuemap and valuemap["sentido"] == self.mappingType)):
                                                      mappedFeat[attmap[key_attr_destiny]] = valuemap[key_value_destiny]

                              if "mapeamento_multiplo" in classmap:
                                  for attmap in classmap['mapeamento_multiplo']:
                                      if "sentido" not in attmap or ("sentido" in attmap and attmap["sentido"] == self.mappingType):
                                          if all([self.evaluateExpression(featDict, condition) for condition in attmap[key_group_origin]]):
                                              for valuemap in attmap[key_group_destiny]:
                                                  if "concatenar" in valuemap and valuemap["concatenar"] and valuemap["nome_atributo"] in mappedFeat and mappedFeat[valuemap["nome_atributo"]]:
                                                      mappedFeat[valuemap["nome_atributo"]] = mappedFeat[valuemap["nome_atributo"]] + ' | ' + valuemap["valor"]
                                                  else:
                                                      mappedFeat[valuemap["nome_atributo"]] = valuemap["valor"]

                              if key_agregar in classmap:
                                  mappedFeat["AGGREGATE_GEOM"] = classmap[key_agregar]
                              elif key_agregar in self.mappingDict:
                                  mappedFeat["AGGREGATE_GEOM"] = self.mappingDict[key_agregar]

                              break

              return mappedFeat

          def mapDictToFeature(self, feat, featDict):
              for attr, value in featDict.iteritems():
                  if value or value == 0:
                      feat.setAttribute(attr, u'{0}'.format(value))
                  else:
                      feat.setAttribute(attr, None)
              if "AGGREGATE_GEOM" in featDict and featDict["AGGREGATE_GEOM"]:
                  feat.buildAggregateFeat([feat])
              return feat

          def input(self,feature):
              if feature.performFunction('@GeometryType()') == 'fme_aggregate':
                  features = feature.splitAggregate(True)
              else:
                  features = [feature]
              for simple_feature in features:
                  feat = self.buildFeatureDict(simple_feature)
                  outputFeatDict = self.convertFeature(feat)
                  if "CLASS_NOT_FOUND" in outputFeatDict and not outputFeatDict["CLASS_NOT_FOUND"]:
                      simple_feature.setAttribute("CLASS_NOT_FOUND", u'True')
                      self.pyoutput(simple_feature)
                  else:
                      outputFeature = self.mapDictToFeature(simple_feature, outputFeatDict)
                      self.pyoutput(outputFeature)

          def close(self):
              pass
    PYTHONSYMBOL = FeatureProcessor
    -> Tester_4
    -> PythonCaller_TRD_EDGV30_Output
PythonCaller_TRD_EDGV30_Output: Inspector
    TACKATTRS = fme_feature_type
Note: Teste de mapeamento
Tester_4
    BOOL_OP = OR
    TEST_CLAUSE = TEST @Value(CLASS_NOT_FOUND) = True
    TEST_MODE = TEST
    PASSED -> AttributeCreator
    FAILED -> PythonCaller_EDGV3_EDGV3PRO
Note: mapeamento
PythonCaller_EDGV3_EDGV3PRO
    NEW_ATTRIBUTES = CLASS_NOT_FOUND
    PYTHONSOURCE:
      import fme
      import fmeobjects
      import copy
      import sys
      import os
      import json

      class FeatureProcessor(object):
          def __init__(self):
              self.mappingDict = self.buildFileDict(FME_MacroValues['JsonMapeamento2'])
              self.mappingType = FME_MacroValues['direcao']

          def buildFileDict(self, mappingPath):
              file = open(mappingPath, 'r')
              data = file.read()
              mapDict = json.loads(data)
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          featDict[attr] = feature.getAttribute(attr)
                      else:
                          featDict[attr] = None
              if feature.performFunction('@GeometryType()') == 'fme_polygon' or feature.performFunction('@GeometryType()') == 'fme_donut':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              else:
                  featDict["$GEOM_TYPE"] = 'NULL'
              return featDict

          def evaluateExpression(self, featDict, expression):
              return expression["nome_atributo"] in featDict and u"{0}".format(featDict[expression["nome_atributo"]]) == u"{0}".format(expression["valor"])

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "ida":
                  key_attr_origin = "attr_ida"
                  key_attr_destiny = "attr_volta"
                  key_value_origin = "valor_ida"
                  key_value_destiny = "valor_volta"
                  key_default = "atributos_default_ida"
                  key_filter = "filtro_ida"
                  key_class_origin = "classe_ida"
                  key_class_destiny = "classe_volta"
                  key_group_origin = "tupla_ida"
                  key_group_destiny = "tupla_volta"
                  key_affix_origin = "afixo_geom_ida"
                  key_affix_destiny = "afixo_geom_volta"
                  key_schema_origin = "schema_ida"
                  key_schema_destiny = "schema_volta"
                  key_class_affix_origin = "com_afixo_geom_ida"
                  key_class_affix_destiny = "com_afixo_geom_volta"
                  key_class_schema_origin = "com_schema_ida"
                  key_class_schema_destiny = "com_schema_volta"
                  key_agregar = "agregar_geom_ida"
              else:
                  key_attr_origin = "attr_volta"
                  key_attr_destiny = "attr_ida"
                  key_value_origin = "valor_volta"
                  key_value_destiny = "valor_ida"
                  key_default = "atributos_default_volta"
                  key_filter = "filtro_volta"
                  key_class_origin = "classe_volta"
                  key_class_destiny = "classe_ida"
                  key_group_origin = "tupla_volta"
                  key_group_destiny = "tupla_ida"
                  key_affix_origin = "afixo_geom_volta"
                  key_affix_destiny = "afixo_geom_ida"
                  key_schema_origin = "schema_volta"
                  key_schema_destiny = "schema_ida"
                  key_class_affix_origin = "com_afixo_geom_volta"
                  key_class_affix_destiny = "com_afixo_geom_ida"
                  key_class_schema_origin = "com_schema_volta"
                  key_class_schema_destiny = "com_schema_ida"
                  key_agregar = "agregar_geom_volta"

              featDict["fme_feature_type_original"] = featDict["fme_feature_type"]

              if key_schema_origin in self.mappingDict and self.mappingDict[key_schema_origin]:
                  featDict["fme_feature_type"] = featDict["fme_feature_type"][len(self.mappingDict[key_schema_origin])+1:]

              featDict["fme_feature_type_sem_schema"] = featDict["fme_feature_type"]

              if key_affix_origin in self.mappingDict and 'tipo' in self.mappingDict[key_affix_origin] and self.mappingDict[key_affix_origin]['tipo'] == 'sufixo':
                  featDict["fme_feature_type"] = featDict["fme_feature_type"][:-len(self.mappingDict[key_affix_origin][featDict["$GEOM_TYPE"]])]
                  featDict["fme_feature_type_sem_afixo"] = featDict["fme_feature_type_original"][:-len(self.mappingDict[key_affix_origin][featDict["$GEOM_TYPE"]])]

              if key_affix_origin in self.mappingDict and 'tipo' in self.mappingDict[key_affix_origin] and self.mappingDict[key_affix_origin]['tipo'] == 'prefixo':
                  featDict["fme_feature_type"] = featDict["fme_feature_type"][len(self.mappingDict[key_affix_origin][featDict["$GEOM_TYPE"]]):]
                  featDict["fme_feature_type_sem_afixo"] = featDict["fme_feature_type_original"][len(self.mappingDict[key_affix_origin][featDict["$GEOM_TYPE"]]):]

              should_map = False
              for classmap in self.mappingDict['mapeamento_classes']:
                  if "sentido" not in classmap or ("sentido" in classmap and classmap["sentido"] == self.mappingType):
                      if key_class_affix_origin in classmap and classmap[key_class_affix_origin] and key_class_schema_origin in classmap and classmap[key_class_schema_origin]:
                          class_name = featDict["fme_feature_type_original"]
                      elif key_class_affix_origin in classmap and classmap[key_class_affix_origin]:
                          class_name = featDict["fme_feature_type_sem_schema"]
                      elif key_class_schema_origin in classmap and classmap[key_class_schema_origin]:
                          class_name = featDict["fme_feature_type_sem_afixo"]
                      else:
                           class_name = featDict["fme_feature_type"]

                      if classmap[key_class_origin] == class_name:
                          if key_filter in classmap:
                              if not self.evaluateFilter(featDict, classmap[key_filter]):
                                  continue
                          should_map = True
              if not should_map:
                  featDict["CLASS_NOT_FOUND"] = True
                  return featDict

              mappedFeat = copy.deepcopy(featDict)

              if key_default in self.mappingDict:
                  for default in self.mappingDict[key_default]:
                      mappedFeat[default["nome_atributo"]] = default["valor"]

              if 'mapeamento_atributos' in self.mappingDict:
                  for attmap in self.mappingDict['mapeamento_atributos']:
                      if attmap[key_attr_origin] in featDict:
                          mappedFeat[attmap[key_attr_destiny]] = featDict[attmap[key_attr_origin]]
                          if "traducao" in attmap:
                              for valuemap in attmap["traducao"]:
                                  if u"{0}".format(valuemap[key_value_origin]) == u"{0}".format(featDict[attmap[key_attr_origin]]) and ("sentido" not in valuemap or ("sentido" in valuemap and valuemap["sentido"] == self.mappingType)):
                                      mappedFeat[attmap[key_attr_destiny]] = valuemap[key_value_destiny]

              if 'mapeamento_classes' in self.mappingDict:
                  for classmap in self.mappingDict['mapeamento_classes']:
                      if "sentido" not in classmap or ("sentido" in classmap and classmap["sentido"] == self.mappingType):
                          if key_class_affix_origin in classmap and classmap[key_class_affix_origin] and key_class_schema_origin in classmap and classmap[key_class_schema_origin]:
                              class_name = featDict["fme_feature_type_original"]
                          elif key_class_affix_origin in classmap and classmap[key_class_affix_origin]:
                              class_name = featDict["fme_feature_type_sem_schema"]
                          elif key_class_schema_origin in classmap and classmap[key_class_schema_origin]:
                              class_name = featDict["fme_feature_type_sem_afixo"]
                          else:
                              class_name = featDict["fme_feature_type"]

                          if classmap[key_class_origin] == class_name:
                              if key_filter in classmap:
                                  if not self.evaluateFilter(featDict, classmap[key_filter]):
                                      continue

                              mappedFeat["fme_feature_type"] = classmap[key_class_destiny]

                              if key_class_affix_destiny in classmap and classmap[key_class_affix_destiny]:
                                  pass
                              elif key_affix_destiny in self.mappingDict and 'tipo' in self.mappingDict[key_affix_destiny]:
                                  if self.mappingDict[key_affix_destiny]['tipo'] == 'sufixo':
                                      mappedFeat["fme_feature_type"] = mappedFeat["fme_feature_type"] + self.mappingDict[key_affix_destiny][featDict["$GEOM_TYPE"]]

                                  if self.mappingDict[key_affix_destiny]['tipo'] == 'prefixo':
                                      mappedFeat["fme_feature_type"] = self.mappingDict[key_affix_destiny][featDict["$GEOM_TYPE"]] + mappedFeat["fme_feature_type"]

                              if key_class_schema_destiny in classmap and classmap[key_class_schema_destiny]:
                                  pass
                              elif key_schema_destiny in self.mappingDict and self.mappingDict[key_schema_destiny]:
                                  mappedFeat["fme_feature_type"] = self.mappingDict[key_schema_destiny] + '.' + mappedFeat["fme_feature_type"]


                              if key_default in classmap:
                                  for default in classmap[key_default]:
                                      mappedFeat[default["nome_atributo"]] = default["valor"]

                              if "mapeamento_atributos" in classmap:
                                  for attmap in classmap['mapeamento_atributos']:
                                      if attmap[key_attr_origin] in featDict:
                                          if attmap[key_attr_destiny] not in mappedFeat:
                                              mappedFeat[attmap[key_attr_destiny]] = featDict[attmap[key_attr_origin]]
                                          if "traducao" in attmap:
                                              for valuemap in attmap["traducao"]:
                                                  if u"{0}".format(valuemap[key_value_origin]) == u"{0}".format(featDict[attmap[key_attr_origin]]) and ("sentido" not in valuemap or ("sentido" in valuemap and valuemap["sentido"] == self.mappingType)):
                                                      mappedFeat[attmap[key_attr_destiny]] = valuemap[key_value_destiny]

                              if "mapeamento_multiplo" in classmap:
                                  for attmap in classmap['mapeamento_multiplo']:
                                      if "sentido" not in attmap or ("sentido" in attmap and attmap["sentido"] == self.mappingType):
                                          if all([self.evaluateExpression(featDict, condition) for condition in attmap[key_group_origin]]):
                                              for valuemap in attmap[key_group_destiny]:
                                                  if "concatenar" in valuemap and valuemap["concatenar"] and valuemap["nome_atributo"] in mappedFeat and mappedFeat[valuemap["nome_atributo"]]:
                                                      mappedFeat[valuemap["nome_atributo"]] = mappedFeat[valuemap["nome_atributo"]] + ' | ' + valuemap["valor"]
                                                  else:
                                                      mappedFeat[valuemap["nome_atributo"]] = valuemap["valor"]

                              if key_agregar in classmap:
                                  mappedFeat["AGGREGATE_GEOM"] = classmap[key_agregar]
                              elif key_agregar in self.mappingDict:
                                  mappedFeat["AGGREGATE_GEOM"] = self.mappingDict[key_agregar]

                              break

              return mappedFeat

          def mapDictToFeature(self, feat, featDict):
              for attr, value in featDict.iteritems():
                  if value or value == 0:
                      feat.setAttribute(attr, u'{0}'.format(value))
                  else:
                      feat.setAttribute(attr, None)
              if "AGGREGATE_GEOM" in featDict and featDict["AGGREGATE_GEOM"]:
                  feat.buildAggregateFeat([feat])
              return feat

          def input(self,feature):
              if feature.performFunction('@GeometryType()') == 'fme_aggregate':
                  features = feature.splitAggregate(True)
              else:
                  features = [feature]
              for simple_feature in features:
                  feat = self.buildFeatureDict(simple_feature)
                  outputFeatDict = self.convertFeature(feat)
                  if "CLASS_NOT_FOUND" in outputFeatDict and not outputFeatDict["CLASS_NOT_FOUND"]:
                      simple_feature.setAttribute("CLASS_NOT_FOUND", u'True')
                      self.pyoutput(simple_feature)
                  else:
                      outputFeature = self.mapDictToFeature(simple_feature, outputFeatDict)
                      self.pyoutput(outputFeature)

          def close(self):
              pass
    PYTHONSYMBOL = FeatureProcessor
    -> Tester_2
    -> PythonCaller_EDGV3_EDGV3PRO_Output
Note: Teste de mapeamento
Tester_2
    BOOL_OP = OR
    TEST_CLAUSE = TEST @Value(CLASS_NOT_FOUND) = True
    TEST_MODE = TEST
    PASSED -> AttributeCreator
    FAILED -> UUIDGenerator
AttributeCreator [off]
    ATTR_TABLE:
      SET_TO descricao = @Value(fme_feature_type)
      SET_TO corrigido = false
    -> GeometryRefiner
GeometryRefiner
    -> GeometryFilter_2
GeometryFilter_2
    BREAK_AGG = No
    GEOM_PORT_NAMES = Point Line Area
    POINT -> Counter
    LINE -> Counter_2
    AREA -> Counter_3
    <UNFILTERED> -> GEOMETRIA_INVALIDA
Counter
    CNT_ATTR = _count
    DOMAIN = counter
    SCOPE = Global
    START = 0
    -> Aggregator
Aggregator
    ACCUM_ATTRS_NAME = Use Attributes From One Feature
    AGGREGATE_TYPE = Homogeneous Collection (If Possible)
    GROUP_BY = _count
    MODE = Geometry - Assemble One Level
    ORDERED = No
    SEP = ,
    AGGREGATE -> aux_revisao_p (writer POSTGIS_3)
aux_revisao_p (writer POSTGIS_3)
    attributes: id serial, descricao varchar(255), subfase_id int4, corrigido bool, justificativa varchar(255), observacao varchar(255), data_modificacao timestamptz, controle_uuid varchar(255), usuario_criacao varchar(255), usuario_atualizacao varchar(255), insumo varchar(255), data_insumo timestamptz
Counter_2
    CNT_ATTR = _count
    DOMAIN = counter
    SCOPE = Global
    START = 0
    -> Aggregator_2
Aggregator_2
    ACCUM_ATTRS_NAME = Use Attributes From One Feature
    AGGREGATE_TYPE = Homogeneous Collection (If Possible)
    GROUP_BY = _count
    MODE = Geometry - Assemble One Level
    ORDERED = No
    SEP = ,
    AGGREGATE -> aux_revisao_l (writer POSTGIS_3)
aux_revisao_l (writer POSTGIS_3)
    attributes: id serial, descricao varchar(255), subfase_id int4, corrigido bool, justificativa varchar(255), observacao varchar(255), data_modificacao timestamptz, controle_uuid varchar(255), usuario_criacao varchar(255), usuario_atualizacao varchar(255), insumo varchar(255), data_insumo timestamptz
Counter_3
    CNT_ATTR = _count
    DOMAIN = counter
    SCOPE = Global
    START = 0
    -> Aggregator_3
Aggregator_3
    ACCUM_ATTRS_NAME = Use Attributes From One Feature
    AGGREGATE_TYPE = Homogeneous Collection (If Possible)
    GROUP_BY = _count
    MODE = Geometry - Assemble One Level
    ORDERED = No
    SEP = ,
    AGGREGATE -> aux_revisao_a (writer POSTGIS_3)
aux_revisao_a (writer POSTGIS_3)
    attributes: id serial, descricao varchar(255), subfase_id int4, corrigido bool, justificativa varchar(255), observacao varchar(255), data_modificacao timestamptz, controle_uuid varchar(255), usuario_criacao varchar(255), usuario_atualizacao varchar(255), insumo varchar(255), data_insumo timestamptz
GEOMETRIA_INVALIDA: Inspector
UUIDGenerator
    UUID_ATTR = controle_uuid
    -> Table1 (writer POSTGIS_4)
Table1 (writer POSTGIS_4)
PythonCaller_EDGV3_EDGV3PRO_Output: Inspector
    TACKATTRS = fme_feature_type
aquisicao_centroide_area_construida_p (reader POSTGIS_2)
    attributes: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
