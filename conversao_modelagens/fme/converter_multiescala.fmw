FME workspace converter_multiescala.fmw

Parameters:
- SourceDataset_POSTGIS = topo_aman_esa_2024_250k_4674_edgv30topo   # Database
- FEATURE_TYPES = edgv.aux_insumo_externo_a edgv.aux_insumo_externo_l edgv.aux_insumo_externo_p edgv.aux_moldura_a edgv.aux_moldura_area_continua_a edgv.aux_reambulacao_a edgv.aux_reambulacao_l edgv.aux_reambulacao_p edgv.aux_revisao_a edgv.aux_revisao_l edgv.aux_revisao_p edgv.aux_validacao_a edgv.aux_validacao_l edgv.aux_validacao_p edgv.centroide_area_construida_p edgv.centroide_area_sem_dados_p edgv.centroide_elemento_hidrografico_p edgv.centroide_ilha_p edgv.centroide_limite_especial_p edgv.centroide_massa_dagua_p edgv.centroide_vegetacao_p edgv.cobter_area_construida_a edgv.cobter_massa_dagua_a edgv.cobter_vegetacao_a edgv.constr_area_uso_especifico_a edgv.constr_deposito_a edgv.constr_deposito_p edgv.constr_edificacao_a edgv.constr_edificacao_p edgv.constr_extracao_mineral_a edgv.constr_extracao_mineral_p edgv.constr_ocupacao_solo_a edgv.constr_ocupacao_solo_l edgv.constr_ocupacao_solo_p edgv.delimitador_area_construida_l edgv.delimitador_area_sem_dados_l edgv.delimitador_elemento_hidrografico_l edgv.delimitador_limite_especial_l edgv.delimitador_massa_dagua_l edgv.delimitador_vegetacao_l edgv.edicao_area_sem_dados_a edgv.edicao_borda_elemento_hidrografico_l edgv.edicao_grid_edicao_l edgv.edicao_identificador_trecho_rod_p edgv.edicao_limite_especial_l edgv.edicao_limite_legal_l edgv.edicao_ponto_mudanca_p edgv.edicao_simb_area_p edgv.edicao_simb_cota_mestra_l edgv.edicao_simb_direcao_corrente_p edgv.edicao_simb_torre_energia_p edgv.edicao_simb_vegetacao_p edgv.edicao_texto_generico_l edgv.edicao_texto_generico_p edgv.elemnat_curva_nivel_l edgv.elemnat_elemento_fisiografico_a edgv.elemnat_elemento_fisiografico_l edgv.elemnat_elemento_fisiografico_p edgv.elemnat_elemento_hidrografico_a edgv.elemnat_elemento_hidrografico_l edgv.elemnat_elemento_hidrografico_p edgv.elemnat_ilha_a edgv.elemnat_ilha_p edgv.elemnat_ponto_cotado_p edgv.elemnat_sumidouro_vertedouro_p edgv.elemnat_terreno_sujeito_inundacao_a edgv.elemnat_toponimo_fisiografico_natural_l edgv.elemnat_toponimo_fisiografico_natural_p edgv.elemnat_trecho_drenagem_l edgv.infra_alteracao_fisiografica_antropica_l edgv.infra_barragem_a edgv.infra_barragem_l edgv.infra_elemento_energia_a edgv.infra_elemento_energia_l edgv.infra_elemento_energia_p edgv.infra_elemento_infraestrutura_a edgv.infra_elemento_infraestrutura_l edgv.infra_elemento_infraestrutura_p edgv.infra_elemento_viario_l edgv.infra_elemento_viario_p edgv.infra_ferrovia_l edgv.infra_mobilidade_urbana_l edgv.infra_pista_pouso_a edgv.infra_pista_pouso_l edgv.infra_pista_pouso_p edgv.infra_travessia_hidroviaria_l edgv.infra_trecho_duto_l edgv.infra_vala_l edgv.infra_via_deslocamento_l edgv.llp_delimitacao_fisica_l edgv.llp_limite_especial_a edgv.llp_localidade_p edgv.llp_pais_a edgv.llp_ponto_controle_p edgv.llp_unidade_federacao_a
- JsonMapeamento = C:\Diniz\modelagens\edgv_300_topo_multiescala\conversao_pg-edgv-300topo_pg-edgv-300topo-multiescala.json   # Arquivo de mapeamento
- direcao = A=>B   # Direção do mapeamento
- SourceDataset_POSTGIS_9 = topo_aman_esa_2024_100k_4674_edgv30topo   # Database
- FEATURE_TYPES_2 = edgv.aux_insumo_externo_a edgv.aux_insumo_externo_l edgv.aux_insumo_externo_p edgv.aux_moldura_a edgv.aux_moldura_area_continua_a edgv.aux_reambulacao_a edgv.aux_reambulacao_l edgv.aux_reambulacao_p edgv.aux_revisao_a edgv.aux_revisao_l edgv.aux_revisao_p edgv.aux_validacao_a edgv.aux_validacao_l edgv.aux_validacao_p edgv.centroide_area_construida_p edgv.centroide_area_sem_dados_p edgv.centroide_elemento_hidrografico_p edgv.centroide_ilha_p edgv.centroide_limite_especial_p edgv.centroide_massa_dagua_p edgv.centroide_vegetacao_p edgv.cobter_area_construida_a edgv.cobter_massa_dagua_a edgv.cobter_vegetacao_a edgv.constr_area_uso_especifico_a edgv.constr_deposito_a edgv.constr_deposito_p edgv.constr_edificacao_a edgv.constr_edificacao_p edgv.constr_extracao_mineral_a edgv.constr_extracao_mineral_p edgv.constr_ocupacao_solo_a edgv.constr_ocupacao_solo_l edgv.constr_ocupacao_solo_p edgv.delimitador_area_construida_l edgv.delimitador_area_sem_dados_l edgv.delimitador_elemento_hidrografico_l edgv.delimitador_limite_especial_l edgv.delimitador_massa_dagua_l edgv.delimitador_vegetacao_l edgv.edicao_area_sem_dados_a edgv.edicao_borda_elemento_hidrografico_l edgv.edicao_grid_edicao_l edgv.edicao_identificador_trecho_rod_p edgv.edicao_limite_especial_l edgv.edicao_limite_legal_l edgv.edicao_ponto_mudanca_p edgv.edicao_simb_area_p edgv.edicao_simb_cota_mestra_l edgv.edicao_simb_direcao_corrente_p edgv.edicao_simb_torre_energia_p edgv.edicao_simb_vegetacao_p edgv.edicao_texto_generico_l edgv.edicao_texto_generico_p edgv.elemnat_curva_nivel_l edgv.elemnat_elemento_fisiografico_a edgv.elemnat_elemento_fisiografico_l edgv.elemnat_elemento_fisiografico_p edgv.elemnat_elemento_hidrografico_a edgv.elemnat_elemento_hidrografico_l edgv.elemnat_elemento_hidrografico_p edgv.elemnat_ilha_a edgv.elemnat_ilha_p edgv.elemnat_ponto_cotado_p edgv.elemnat_sumidouro_vertedouro_p edgv.elemnat_terreno_sujeito_inundacao_a edgv.elemnat_toponimo_fisiografico_natural_l edgv.elemnat_toponimo_fisiografico_natural_p edgv.elemnat_trecho_drenagem_l edgv.infra_alteracao_fisiografica_antropica_l edgv.infra_barragem_a edgv.infra_barragem_l edgv.infra_elemento_energia_a edgv.infra_elemento_energia_l edgv.infra_elemento_energia_p edgv.infra_elemento_infraestrutura_a edgv.infra_elemento_infraestrutura_l edgv.infra_elemento_infraestrutura_p edgv.infra_elemento_viario_l edgv.infra_elemento_viario_p edgv.infra_ferrovia_l edgv.infra_mobilidade_urbana_l edgv.infra_pista_pouso_a edgv.infra_pista_pouso_l edgv.infra_pista_pouso_p edgv.infra_travessia_hidroviaria_l edgv.infra_trecho_duto_l edgv.infra_vala_l edgv.infra_via_deslocamento_l edgv.llp_delimitacao_fisica_l edgv.llp_limite_especial_a edgv.llp_localidade_p edgv.llp_pais_a edgv.llp_ponto_controle_p edgv.llp_unidade_federacao_a
- SourceDataset_POSTGIS_11 = topo_aman_esa_2024_50k_4674_edgv30topo   # Database
- FEATURE_TYPES_3 = edgv.aux_insumo_externo_a edgv.aux_insumo_externo_l edgv.aux_insumo_externo_p edgv.aux_moldura_a edgv.aux_moldura_area_continua_a edgv.aux_reambulacao_a edgv.aux_reambulacao_l edgv.aux_reambulacao_p edgv.aux_revisao_a edgv.aux_revisao_l edgv.aux_revisao_p edgv.aux_validacao_a edgv.aux_validacao_l edgv.aux_validacao_p edgv.centroide_area_construida_p edgv.centroide_area_sem_dados_p edgv.centroide_elemento_hidrografico_p edgv.centroide_ilha_p edgv.centroide_limite_especial_p edgv.centroide_massa_dagua_p edgv.centroide_vegetacao_p edgv.cobter_area_construida_a edgv.cobter_massa_dagua_a edgv.cobter_vegetacao_a edgv.constr_area_uso_especifico_a edgv.constr_deposito_a edgv.constr_deposito_p edgv.constr_edificacao_a edgv.constr_edificacao_p edgv.constr_extracao_mineral_a edgv.constr_extracao_mineral_p edgv.constr_ocupacao_solo_a edgv.constr_ocupacao_solo_l edgv.constr_ocupacao_solo_p edgv.delimitador_area_construida_l edgv.delimitador_area_sem_dados_l edgv.delimitador_elemento_hidrografico_l edgv.delimitador_limite_especial_l edgv.delimitador_massa_dagua_l edgv.delimitador_vegetacao_l edgv.edicao_area_sem_dados_a edgv.edicao_borda_elemento_hidrografico_l edgv.edicao_grid_edicao_l edgv.edicao_identificador_trecho_rod_p edgv.edicao_limite_especial_l edgv.edicao_limite_legal_l edgv.edicao_ponto_mudanca_p edgv.edicao_simb_area_p edgv.edicao_simb_cota_mestra_l edgv.edicao_simb_direcao_corrente_p edgv.edicao_simb_torre_energia_p edgv.edicao_simb_vegetacao_p edgv.edicao_texto_generico_l edgv.edicao_texto_generico_p edgv.elemnat_curva_nivel_l edgv.elemnat_elemento_fisiografico_a edgv.elemnat_elemento_fisiografico_l edgv.elemnat_elemento_fisiografico_p edgv.elemnat_elemento_hidrografico_a edgv.elemnat_elemento_hidrografico_l edgv.elemnat_elemento_hidrografico_p edgv.elemnat_ilha_a edgv.elemnat_ilha_p edgv.elemnat_ponto_cotado_p edgv.elemnat_sumidouro_vertedouro_p edgv.elemnat_terreno_sujeito_inundacao_a edgv.elemnat_toponimo_fisiografico_natural_l edgv.elemnat_toponimo_fisiografico_natural_p edgv.elemnat_trecho_drenagem_l edgv.infra_alteracao_fisiografica_antropica_l edgv.infra_barragem_a edgv.infra_barragem_l edgv.infra_elemento_energia_a edgv.infra_elemento_energia_l edgv.infra_elemento_energia_p edgv.infra_elemento_infraestrutura_a edgv.infra_elemento_infraestrutura_l edgv.infra_elemento_infraestrutura_p edgv.infra_elemento_viario_l edgv.infra_elemento_viario_p edgv.infra_ferrovia_l edgv.infra_mobilidade_urbana_l edgv.infra_pista_pouso_a edgv.infra_pista_pouso_l edgv.infra_pista_pouso_p edgv.infra_travessia_hidroviaria_l edgv.infra_trecho_duto_l edgv.infra_vala_l edgv.infra_via_deslocamento_l edgv.llp_delimitacao_fisica_l edgv.llp_limite_especial_a edgv.llp_localidade_p edgv.llp_pais_a edgv.llp_ponto_controle_p edgv.llp_unidade_federacao_a
- SourceDataset_POSTGIS_6 = topo_aman_esa_2024_25k_4674_edgv30topo   # Database
- FEATURE_TYPES_4 = edgv.aux_insumo_externo_a edgv.aux_insumo_externo_l edgv.aux_insumo_externo_p edgv.aux_moldura_a edgv.aux_moldura_area_continua_a edgv.aux_reambulacao_a edgv.aux_reambulacao_l edgv.aux_reambulacao_p edgv.aux_revisao_a edgv.aux_revisao_l edgv.aux_revisao_p edgv.aux_validacao_a edgv.aux_validacao_l edgv.aux_validacao_p edgv.centroide_area_construida_p edgv.centroide_area_sem_dados_p edgv.centroide_elemento_hidrografico_p edgv.centroide_ilha_p edgv.centroide_limite_especial_p edgv.centroide_massa_dagua_p edgv.centroide_vegetacao_p edgv.cobter_area_construida_a edgv.cobter_massa_dagua_a edgv.cobter_vegetacao_a edgv.constr_area_uso_especifico_a edgv.constr_deposito_a edgv.constr_deposito_p edgv.constr_edificacao_a edgv.constr_edificacao_p edgv.constr_extracao_mineral_a edgv.constr_extracao_mineral_p edgv.constr_ocupacao_solo_a edgv.constr_ocupacao_solo_l edgv.constr_ocupacao_solo_p edgv.delimitador_area_construida_l edgv.delimitador_area_sem_dados_l edgv.delimitador_elemento_hidrografico_l edgv.delimitador_limite_especial_l edgv.delimitador_massa_dagua_l edgv.delimitador_vegetacao_l edgv.edicao_area_sem_dados_a edgv.edicao_borda_elemento_hidrografico_l edgv.edicao_grid_edicao_l edgv.edicao_identificador_trecho_rod_p edgv.edicao_limite_especial_l edgv.edicao_limite_legal_l edgv.edicao_ponto_mudanca_p edgv.edicao_simb_area_p edgv.edicao_simb_cota_mestra_l edgv.edicao_simb_direcao_corrente_p edgv.edicao_simb_torre_energia_p edgv.edicao_simb_vegetacao_p edgv.edicao_texto_generico_l edgv.edicao_texto_generico_p edgv.elemnat_curva_nivel_l edgv.elemnat_elemento_fisiografico_a edgv.elemnat_elemento_fisiografico_l edgv.elemnat_elemento_fisiografico_p edgv.elemnat_elemento_hidrografico_a edgv.elemnat_elemento_hidrografico_l edgv.elemnat_elemento_hidrografico_p edgv.elemnat_ilha_a edgv.elemnat_ilha_p edgv.elemnat_ponto_cotado_p edgv.elemnat_sumidouro_vertedouro_p edgv.elemnat_terreno_sujeito_inundacao_a edgv.elemnat_toponimo_fisiografico_natural_l edgv.elemnat_toponimo_fisiografico_natural_p edgv.elemnat_trecho_drenagem_l edgv.infra_alteracao_fisiografica_antropica_l edgv.infra_barragem_a edgv.infra_barragem_l edgv.infra_elemento_energia_a edgv.infra_elemento_energia_l edgv.infra_elemento_energia_p edgv.infra_elemento_infraestrutura_a edgv.infra_elemento_infraestrutura_l edgv.infra_elemento_infraestrutura_p edgv.infra_elemento_viario_l edgv.infra_elemento_viario_p edgv.infra_ferrovia_l edgv.infra_mobilidade_urbana_l edgv.infra_pista_pouso_a edgv.infra_pista_pouso_l edgv.infra_pista_pouso_p edgv.infra_travessia_hidroviaria_l edgv.infra_trecho_duto_l edgv.infra_vala_l edgv.infra_via_deslocamento_l edgv.llp_delimitacao_fisica_l edgv.llp_limite_especial_a edgv.llp_localidade_p edgv.llp_pais_a edgv.llp_ponto_controle_p edgv.llp_unidade_federacao_a
- SourceDataset_POSTGIS_13 = topo_aman_esa_2024_10k_4674_edgv30topo   # Database
- FEATURE_TYPES_5 = edgv.aux_insumo_externo_a edgv.aux_insumo_externo_l edgv.aux_insumo_externo_p edgv.aux_moldura_a edgv.aux_moldura_area_continua_a edgv.aux_reambulacao_a edgv.aux_reambulacao_l edgv.aux_reambulacao_p edgv.aux_revisao_a edgv.aux_revisao_l edgv.aux_revisao_p edgv.aux_validacao_a edgv.aux_validacao_l edgv.aux_validacao_p edgv.centroide_area_construida_p edgv.centroide_area_sem_dados_p edgv.centroide_elemento_hidrografico_p edgv.centroide_ilha_p edgv.centroide_limite_especial_p edgv.centroide_massa_dagua_p edgv.centroide_vegetacao_p edgv.cobter_area_construida_a edgv.cobter_massa_dagua_a edgv.cobter_vegetacao_a edgv.constr_area_uso_especifico_a edgv.constr_deposito_a edgv.constr_deposito_p edgv.constr_edificacao_a edgv.constr_edificacao_p edgv.constr_extracao_mineral_a edgv.constr_extracao_mineral_p edgv.constr_ocupacao_solo_a edgv.constr_ocupacao_solo_l edgv.constr_ocupacao_solo_p edgv.delimitador_area_construida_l edgv.delimitador_area_sem_dados_l edgv.delimitador_elemento_hidrografico_l edgv.delimitador_limite_especial_l edgv.delimitador_massa_dagua_l edgv.delimitador_vegetacao_l edgv.edicao_area_sem_dados_a edgv.edicao_borda_elemento_hidrografico_l edgv.edicao_grid_edicao_l edgv.edicao_identificador_trecho_rod_p edgv.edicao_limite_especial_l edgv.edicao_limite_legal_l edgv.edicao_ponto_mudanca_p edgv.edicao_simb_area_p edgv.edicao_simb_cota_mestra_l edgv.edicao_simb_direcao_corrente_p edgv.edicao_simb_torre_energia_p edgv.edicao_simb_vegetacao_p edgv.edicao_texto_generico_l edgv.edicao_texto_generico_p edgv.elemnat_curva_nivel_l edgv.elemnat_elemento_fisiografico_a edgv.elemnat_elemento_fisiografico_l edgv.elemnat_elemento_fisiografico_p edgv.elemnat_elemento_hidrografico_a edgv.elemnat_elemento_hidrografico_l edgv.elemnat_elemento_hidrografico_p edgv.elemnat_ilha_a edgv.elemnat_ilha_p edgv.elemnat_ponto_cotado_p edgv.elemnat_sumidouro_vertedouro_p edgv.elemnat_terreno_sujeito_inundacao_a edgv.elemnat_toponimo_fisiografico_natural_l edgv.elemnat_toponimo_fisiografico_natural_p edgv.elemnat_trecho_drenagem_l edgv.infra_alteracao_fisiografica_antropica_l edgv.infra_barragem_a edgv.infra_barragem_l edgv.infra_elemento_energia_a edgv.infra_elemento_energia_l edgv.infra_elemento_energia_p edgv.infra_elemento_infraestrutura_a edgv.infra_elemento_infraestrutura_l edgv.infra_elemento_infraestrutura_p edgv.infra_elemento_viario_l edgv.infra_elemento_viario_p edgv.infra_ferrovia_l edgv.infra_mobilidade_urbana_l edgv.infra_pista_pouso_a edgv.infra_pista_pouso_l edgv.infra_pista_pouso_p edgv.infra_travessia_hidroviaria_l edgv.infra_trecho_duto_l edgv.infra_vala_l edgv.infra_via_deslocamento_l edgv.llp_delimitacao_fisica_l edgv.llp_limite_especial_a edgv.llp_localidade_p edgv.llp_pais_a edgv.llp_ponto_controle_p edgv.llp_unidade_federacao_a
- DestDataset_POSTGIS = multiescala   # Database
- SourceDataset_POSTGIS_10 = multiescala   # Database
- FEATURE_TYPES_6 = edgv.aux_insumo_externo_100k_a edgv.aux_insumo_externo_100k_l edgv.aux_insumo_externo_100k_p edgv.aux_insumo_externo_10k_a edgv.aux_insumo_externo_10k_l edgv.aux_insumo_externo_10k_p edgv.aux_insumo_externo_250k_a edgv.aux_insumo_externo_250k_l edgv.aux_insumo_externo_250k_p edgv.aux_insumo_externo_25k_a edgv.aux_insumo_externo_25k_l edgv.aux_insumo_externo_25k_p edgv.aux_insumo_externo_50k_a edgv.aux_insumo_externo_50k_l edgv.aux_insumo_externo_50k_p edgv.aux_moldura_100k_a edgv.aux_moldura_10k_a edgv.aux_moldura_250k_a edgv.aux_moldura_25k_a edgv.aux_moldura_50k_a edgv.aux_moldura_area_continua_100k_a edgv.aux_moldura_area_continua_10k_a edgv.aux_moldura_area_continua_250k_a edgv.aux_moldura_area_continua_25k_a edgv.aux_moldura_area_continua_50k_a edgv.aux_reambulacao_100k_a edgv.aux_reambulacao_100k_l edgv.aux_reambulacao_100k_p edgv.aux_reambulacao_10k_a edgv.aux_reambulacao_10k_l edgv.aux_reambulacao_10k_p edgv.aux_reambulacao_250k_a edgv.aux_reambulacao_250k_l edgv.aux_reambulacao_250k_p edgv.aux_reambulacao_25k_a edgv.aux_reambulacao_25k_l edgv.aux_reambulacao_25k_p edgv.aux_reambulacao_50k_a edgv.aux_reambulacao_50k_l edgv.aux_reambulacao_50k_p edgv.aux_revisao_100k_a edgv.aux_revisao_100k_l edgv.aux_revisao_100k_p edgv.aux_revisao_10k_a edgv.aux_revisao_10k_l edgv.aux_revisao_10k_p edgv.aux_revisao_250k_a edgv.aux_revisao_250k_l edgv.aux_revisao_250k_p edgv.aux_revisao_25k_a edgv.aux_revisao_25k_l edgv.aux_revisao_25k_p edgv.aux_revisao_50k_a edgv.aux_revisao_50k_l edgv.aux_revisao_50k_p edgv.aux_validacao_100k_a edgv.aux_validacao_100k_l edgv.aux_validacao_100k_p edgv.aux_validacao_10k_a edgv.aux_validacao_10k_l edgv.aux_validacao_10k_p edgv.aux_validacao_250k_a edgv.aux_validacao_250k_l edgv.aux_validacao_250k_p edgv.aux_validacao_25k_a edgv.aux_validacao_25k_l edgv.aux_validacao_25k_p edgv.aux_validacao_50k_a edgv.aux_validacao_50k_l edgv.aux_validacao_50k_p edgv.centroide_area_construida_100k_p edgv.centroide_area_construida_10k_p edgv.centroide_area_construida_250k_p edgv.centroide_area_construida_25k_p edgv.centroide_area_construida_50k_p edgv.centroide_area_sem_dados_100k_p edgv.centroide_area_sem_dados_10k_p edgv.centroide_area_sem_dados_250k_p edgv.centroide_area_sem_dados_25k_p edgv.centroide_area_sem_dados_50k_p edgv.centroide_elemento_hidrografico_100k_p edgv.centroide_elemento_hidrografico_10k_p edgv.centroide_elemento_hidrografico_250k_p edgv.centroide_elemento_hidrografico_25k_p edgv.centroide_elemento_hidrografico_50k_p edgv.centroide_ilha_100k_p edgv.centroide_ilha_10k_p edgv.centroide_ilha_250k_p edgv.centroide_ilha_25k_p edgv.centroide_ilha_50k_p edgv.centroide_limite_especial_100k_p edgv.centroide_limite_especial_10k_p edgv.centroide_limite_especial_250k_p edgv.centroide_limite_especial_25k_p edgv.centroide_limite_especial_50k_p edgv.centroide_massa_dagua_100k_p edgv.centroide_massa_dagua_10k_p edgv.centroide_massa_dagua_250k_p edgv.centroide_massa_dagua_25k_p edgv.centroide_massa_dagua_50k_p edgv.centroide_vegetacao_100k_p edgv.centroide_vegetacao_10k_p edgv.centroide_vegetacao_250k_p edgv.centroide_vegetacao_25k_p edgv.centroide_vegetacao_50k_p edgv.cobter_area_construida_100k_a edgv.cobter_area_construida_10k_a edgv.cobter_area_construida_250k_a edgv.cobter_area_construida_25k_a edgv.cobter_area_construida_50k_a edgv.cobter_massa_dagua_100k_a edgv.cobter_massa_dagua_10k_a edgv.cobter_massa_dagua_250k_a edgv.cobter_massa_dagua_25k_a edgv.cobter_massa_dagua_50k_a edgv.cobter_vegetacao_100k_a edgv.cobter_vegetacao_10k_a edgv.cobter_vegetacao_250k_a edgv.cobter_vegetacao_25k_a edgv.cobter_vegetacao_50k_a edgv.constr_area_uso_especifico_100k_a edgv.constr_area_uso_especifico_10k_a edgv.constr_area_uso_especifico_250k_a edgv.constr_area_uso_especifico_25k_a edgv.constr_area_uso_especifico_50k_a edgv.constr_deposito_100k_a edgv.constr_deposito_100k_p edgv.constr_deposito_10k_a edgv.constr_deposito_10k_p edgv.constr_deposito_250k_a edgv.constr_deposito_250k_p edgv.constr_deposito_25k_a edgv.constr_deposito_25k_p edgv.constr_deposito_50k_a edgv.constr_deposito_50k_p edgv.constr_edificacao_100k_a edgv.constr_edificacao_100k_p edgv.constr_edificacao_10k_a edgv.constr_edificacao_10k_p edgv.constr_edificacao_250k_a edgv.constr_edificacao_250k_p edgv.constr_edificacao_25k_a edgv.constr_edificacao_25k_p edgv.constr_edificacao_50k_a edgv.constr_edificacao_50k_p edgv.constr_extracao_mineral_100k_a edgv.constr_extracao_mineral_100k_p edgv.constr_extracao_mineral_10k_a edgv.constr_extracao_mineral_10k_p edgv.constr_extracao_mineral_250k_a edgv.constr_extracao_mineral_250k_p edgv.constr_extracao_mineral_25k_a edgv.constr_extracao_mineral_25k_p edgv.constr_extracao_mineral_50k_a edgv.constr_extracao_mineral_50k_p edgv.constr_ocupacao_solo_100k_a edgv.constr_ocupacao_solo_100k_l edgv.constr_ocupacao_solo_100k_p edgv.constr_ocupacao_solo_10k_a edgv.constr_ocupacao_solo_10k_l edgv.constr_ocupacao_solo_10k_p edgv.constr_ocupacao_solo_250k_a edgv.constr_ocupacao_solo_250k_l edgv.constr_ocupacao_solo_250k_p edgv.constr_ocupacao_solo_25k_a edgv.constr_ocupacao_solo_25k_l edgv.constr_ocupacao_solo_25k_p edgv.constr_ocupacao_solo_50k_a edgv.constr_ocupacao_solo_50k_l edgv.constr_ocupacao_solo_50k_p edgv.delimitador_area_construida_100k_l edgv.delimitador_area_construida_10k_l edgv.delimitador_area_construida_250k_l edgv.delimitador_area_construida_25k_l edgv.delimitador_area_construida_50k_l edgv.delimitador_area_sem_dados_100k_l edgv.delimitador_area_sem_dados_10k_l edgv.delimitador_area_sem_dados_250k_l edgv.delimitador_area_sem_dados_25k_l edgv.delimitador_area_sem_dados_50k_l edgv.delimitador_elemento_hidrografico_100k_l edgv.delimitador_elemento_hidrografico_10k_l edgv.delimitador_elemento_hidrografico_250k_l edgv.delimitador_elemento_hidrografico_25k_l edgv.delimitador_elemento_hidrografico_50k_l edgv.delimitador_limite_especial_100k_l edgv.delimitador_limite_especial_10k_l edgv.delimitador_limite_especial_250k_l edgv.delimitador_limite_especial_25k_l edgv.delimitador_limite_especial_50k_l edgv.delimitador_massa_dagua_100k_l edgv.delimitador_massa_dagua_10k_l edgv.delimitador_massa_dagua_250k_l edgv.delimitador_massa_dagua_25k_l edgv.delimitador_massa_dagua_50k_l edgv.delimitador_vegetacao_100k_l edgv.delimitador_vegetacao_10k_l edgv.delimitador_vegetacao_250k_l edgv.delimitador_vegetacao_25k_l edgv.delimitador_vegetacao_50k_l edgv.edicao_area_sem_dados_100k_a edgv.edicao_area_sem_dados_10k_a edgv.edicao_area_sem_dados_250k_a edgv.edicao_area_sem_dados_25k_a edgv.edicao_area_sem_dados_50k_a edgv.edicao_borda_elemento_hidrografico_100k_l edgv.edicao_borda_elemento_hidrografico_10k_l edgv.edicao_borda_elemento_hidrografico_250k_l edgv.edicao_borda_elemento_hidrografico_25k_l edgv.edicao_borda_elemento_hidrografico_50k_l edgv.edicao_grid_edicao_100k_l edgv.edicao_grid_edicao_10k_l edgv.edicao_grid_edicao_250k_l edgv.edicao_grid_edicao_25k_l edgv.edicao_grid_edicao_50k_l edgv.edicao_identificador_trecho_rod_100k_p edgv.edicao_identificador_trecho_rod_10k_p edgv.edicao_identificador_trecho_rod_250k_p edgv.edicao_identificador_trecho_rod_25k_p edgv.edicao_identificador_trecho_rod_50k_p edgv.edicao_limite_especial_100k_l edgv.edicao_limite_especial_10k_l edgv.edicao_limite_especial_250k_l edgv.edicao_limite_especial_25k_l edgv.edicao_limite_especial_50k_l edgv.edicao_limite_legal_100k_l edgv.edicao_limite_legal_10k_l edgv.edicao_limite_legal_250k_l edgv.edicao_limite_legal_25k_l edgv.edicao_limite_legal_50k_l edgv.edicao_ponto_mudanca_100k_p edgv.edicao_ponto_mudanca_10k_p edgv.edicao_ponto_mudanca_250k_p edgv.edicao_ponto_mudanca_25k_p edgv.edicao_ponto_mudanca_50k_p edgv.edicao_simb_area_100k_p edgv.edicao_simb_area_10k_p edgv.edicao_simb_area_250k_p edgv.edicao_simb_area_25k_p edgv.edicao_simb_area_50k_p edgv.edicao_simb_cota_mestra_100k_l edgv.edicao_simb_cota_mestra_10k_l edgv.edicao_simb_cota_mestra_250k_l edgv.edicao_simb_cota_mestra_25k_l edgv.edicao_simb_cota_mestra_50k_l edgv.edicao_simb_direcao_corrente_100k_p edgv.edicao_simb_direcao_corrente_10k_p edgv.edicao_simb_direcao_corrente_250k_p edgv.edicao_simb_direcao_corrente_25k_p edgv.edicao_simb_direcao_corrente_50k_p edgv.edicao_simb_torre_energia_100k_p edgv.edicao_simb_torre_energia_10k_p edgv.edicao_simb_torre_energia_250k_p edgv.edicao_simb_torre_energia_25k_p edgv.edicao_simb_torre_energia_50k_p edgv.edicao_simb_vegetacao_100k_p edgv.edicao_simb_vegetacao_10k_p edgv.edicao_simb_vegetacao_250k_p edgv.edicao_simb_vegetacao_25k_p edgv.edicao_simb_vegetacao_50k_p edgv.edicao_texto_generico_100k_l edgv.edicao_texto_generico_100k_p edgv.edicao_texto_generico_10k_l edgv.edicao_texto_generico_10k_p edgv.edicao_texto_generico_250k_l edgv.edicao_texto_generico_250k_p edgv.edicao_texto_generico_25k_l edgv.edicao_texto_generico_25k_p edgv.edicao_texto_generico_50k_l edgv.edicao_texto_generico_50k_p edgv.elemnat_curva_nivel_100k_l edgv.elemnat_curva_nivel_10k_l edgv.elemnat_curva_nivel_250k_l edgv.elemnat_curva_nivel_25k_l edgv.elemnat_curva_nivel_50k_l edgv.elemnat_elemento_fisiografico_100k_a edgv.elemnat_elemento_fisiografico_100k_l edgv.elemnat_elemento_fisiografico_100k_p edgv.elemnat_elemento_fisiografico_10k_a edgv.elemnat_elemento_fisiografico_10k_l edgv.elemnat_elemento_fisiografico_10k_p edgv.elemnat_elemento_fisiografico_250k_a edgv.elemnat_elemento_fisiografico_250k_l edgv.elemnat_elemento_fisiografico_250k_p edgv.elemnat_elemento_fisiografico_25k_a edgv.elemnat_elemento_fisiografico_25k_l edgv.elemnat_elemento_fisiografico_25k_p edgv.elemnat_elemento_fisiografico_50k_a edgv.elemnat_elemento_fisiografico_50k_l edgv.elemnat_elemento_fisiografico_50k_p edgv.elemnat_elemento_hidrografico_100k_a edgv.elemnat_elemento_hidrografico_100k_l edgv.elemnat_elemento_hidrografico_100k_p edgv.elemnat_elemento_hidrografico_10k_a edgv.elemnat_elemento_hidrografico_10k_l edgv.elemnat_elemento_hidrografico_10k_p edgv.elemnat_elemento_hidrografico_250k_a edgv.elemnat_elemento_hidrografico_250k_l edgv.elemnat_elemento_hidrografico_250k_p edgv.elemnat_elemento_hidrografico_25k_a edgv.elemnat_elemento_hidrografico_25k_l edgv.elemnat_elemento_hidrografico_25k_p edgv.elemnat_elemento_hidrografico_50k_a edgv.elemnat_elemento_hidrografico_50k_l edgv.elemnat_elemento_hidrografico_50k_p edgv.elemnat_ilha_100k_a edgv.elemnat_ilha_100k_p edgv.elemnat_ilha_10k_a edgv.elemnat_ilha_10k_p edgv.elemnat_ilha_250k_a edgv.elemnat_ilha_250k_p edgv.elemnat_ilha_25k_a edgv.elemnat_ilha_25k_p edgv.elemnat_ilha_50k_a edgv.elemnat_ilha_50k_p edgv.elemnat_ponto_cotado_100k_p edgv.elemnat_ponto_cotado_10k_p edgv.elemnat_ponto_cotado_250k_p edgv.elemnat_ponto_cotado_25k_p edgv.elemnat_ponto_cotado_50k_p edgv.elemnat_sumidouro_vertedouro_100k_p edgv.elemnat_sumidouro_vertedouro_10k_p edgv.elemnat_sumidouro_vertedouro_250k_p edgv.elemnat_sumidouro_vertedouro_25k_p edgv.elemnat_sumidouro_vertedouro_50k_p edgv.elemnat_terreno_sujeito_inundacao_100k_a edgv.elemnat_terreno_sujeito_inundacao_10k_a edgv.elemnat_terreno_sujeito_inundacao_250k_a edgv.elemnat_terreno_sujeito_inundacao_25k_a edgv.elemnat_terreno_sujeito_inundacao_50k_a edgv.elemnat_toponimo_fisiografico_natural_100k_l edgv.elemnat_toponimo_fisiografico_natural_100k_p edgv.elemnat_toponimo_fisiografico_natural_10k_l edgv.elemnat_toponimo_fisiografico_natural_10k_p edgv.elemnat_toponimo_fisiografico_natural_250k_l edgv.elemnat_toponimo_fisiografico_natural_250k_p edgv.elemnat_toponimo_fisiografico_natural_25k_l edgv.elemnat_toponimo_fisiografico_natural_25k_p edgv.elemnat_toponimo_fisiografico_natural_50k_l edgv.elemnat_toponimo_fisiografico_natural_50k_p edgv.elemnat_trecho_drenagem_100k_l edgv.elemnat_trecho_drenagem_10k_l edgv.elemnat_trecho_drenagem_250k_l edgv.elemnat_trecho_drenagem_25k_l edgv.elemnat_trecho_drenagem_50k_l edgv.infra_alteracao_fisiografica_antropica_100k_l edgv.infra_alteracao_fisiografica_antropica_10k_l edgv.infra_alteracao_fisiografica_antropica_250k_l edgv.infra_alteracao_fisiografica_antropica_25k_l edgv.infra_alteracao_fisiografica_antropica_50k_l edgv.infra_barragem_100k_a edgv.infra_barragem_100k_l edgv.infra_barragem_10k_a edgv.infra_barragem_10k_l edgv.infra_barragem_250k_a edgv.infra_barragem_250k_l edgv.infra_barragem_25k_a edgv.infra_barragem_25k_l edgv.infra_barragem_50k_a edgv.infra_barragem_50k_l edgv.infra_elemento_energia_100k_a edgv.infra_elemento_energia_100k_l edgv.infra_elemento_energia_100k_p edgv.infra_elemento_energia_10k_a edgv.infra_elemento_energia_10k_l edgv.infra_elemento_energia_10k_p edgv.infra_elemento_energia_250k_a edgv.infra_elemento_energia_250k_l edgv.infra_elemento_energia_250k_p edgv.infra_elemento_energia_25k_a edgv.infra_elemento_energia_25k_l edgv.infra_elemento_energia_25k_p edgv.infra_elemento_energia_50k_a edgv.infra_elemento_energia_50k_l edgv.infra_elemento_energia_50k_p edgv.infra_elemento_infraestrutura_100k_a edgv.infra_elemento_infraestrutura_100k_l edgv.infra_elemento_infraestrutura_100k_p edgv.infra_elemento_infraestrutura_10k_a edgv.infra_elemento_infraestrutura_10k_l edgv.infra_elemento_infraestrutura_10k_p edgv.infra_elemento_infraestrutura_250k_a edgv.infra_elemento_infraestrutura_250k_l edgv.infra_elemento_infraestrutura_250k_p edgv.infra_elemento_infraestrutura_25k_a edgv.infra_elemento_infraestrutura_25k_l edgv.infra_elemento_infraestrutura_25k_p edgv.infra_elemento_infraestrutura_50k_a edgv.infra_elemento_infraestrutura_50k_l edgv.infra_elemento_infraestrutura_50k_p edgv.infra_elemento_viario_100k_l edgv.infra_elemento_viario_100k_p edgv.infra_elemento_viario_10k_l edgv.infra_elemento_viario_10k_p edgv.infra_elemento_viario_250k_l edgv.infra_elemento_viario_250k_p edgv.infra_elemento_viario_25k_l edgv.infra_elemento_viario_25k_p edgv.infra_elemento_viario_50k_l edgv.infra_elemento_viario_50k_p edgv.infra_ferrovia_100k_l edgv.infra_ferrovia_10k_l edgv.infra_ferrovia_250k_l edgv.infra_ferrovia_25k_l edgv.infra_ferrovia_50k_l edgv.infra_mobilidade_urbana_100k_l edgv.infra_mobilidade_urbana_10k_l edgv.infra_mobilidade_urbana_250k_l edgv.infra_mobilidade_urbana_25k_l edgv.infra_mobilidade_urbana_50k_l edgv.infra_pista_pouso_100k_a edgv.infra_pista_pouso_100k_l edgv.infra_pista_pouso_100k_p edgv.infra_pista_pouso_10k_a edgv.infra_pista_pouso_10k_l edgv.infra_pista_pouso_10k_p edgv.infra_pista_pouso_250k_a edgv.infra_pista_pouso_250k_l edgv.infra_pista_pouso_250k_p edgv.infra_pista_pouso_25k_a edgv.infra_pista_pouso_25k_l edgv.infra_pista_pouso_25k_p edgv.infra_pista_pouso_50k_a edgv.infra_pista_pouso_50k_l edgv.infra_pista_pouso_50k_p edgv.infra_travessia_hidroviaria_100k_l edgv.infra_travessia_hidroviaria_10k_l edgv.infra_travessia_hidroviaria_250k_l edgv.infra_travessia_hidroviaria_25k_l edgv.infra_travessia_hidroviaria_50k_l edgv.infra_trecho_duto_100k_l edgv.infra_trecho_duto_10k_l edgv.infra_trecho_duto_250k_l edgv.infra_trecho_duto_25k_l edgv.infra_trecho_duto_50k_l edgv.infra_vala_100k_l edgv.infra_vala_10k_l edgv.infra_vala_250k_l edgv.infra_vala_25k_l edgv.infra_vala_50k_l edgv.infra_via_deslocamento_100k_l edgv.infra_via_deslocamento_10k_l edgv.infra_via_deslocamento_250k_l edgv.infra_via_deslocamento_25k_l edgv.infra_via_deslocamento_50k_l edgv.llp_delimitacao_fisica_100k_l edgv.llp_delimitacao_fisica_10k_l edgv.llp_delimitacao_fisica_250k_l edgv.llp_delimitacao_fisica_25k_l edgv.llp_delimitacao_fisica_50k_l edgv.llp_limite_especial_100k_a edgv.llp_limite_especial_10k_a edgv.llp_limite_especial_250k_a edgv.llp_limite_especial_25k_a edgv.llp_limite_especial_50k_a edgv.llp_localidade_100k_p edgv.llp_localidade_10k_p edgv.llp_localidade_250k_p edgv.llp_localidade_25k_p edgv.llp_localidade_50k_p edgv.llp_pais_100k_a edgv.llp_pais_10k_a edgv.llp_pais_250k_a edgv.llp_pais_25k_a edgv.llp_pais_50k_a edgv.llp_ponto_controle_100k_p edgv.llp_ponto_controle_10k_p edgv.llp_ponto_controle_250k_p edgv.llp_ponto_controle_25k_p edgv.llp_ponto_controle_50k_p edgv.llp_unidade_federacao_100k_a edgv.llp_unidade_federacao_10k_a edgv.llp_unidade_federacao_250k_a edgv.llp_unidade_federacao_25k_a edgv.llp_unidade_federacao_50k_a
- SourceDataset_OGCGEOPACKAGE = C:\Users\diniz\Downloads\moldura_100k.gpkg   # GeoPackage File
- SourceDataset_POSTGIS_12 = tres_coracoes   # Database
- FEATURE_TYPES_7 = edgv.aux_insumo_externo_a edgv.aux_insumo_externo_l edgv.aux_insumo_externo_p edgv.aux_moldura_a edgv.aux_moldura_area_continua_a edgv.aux_reambulacao_a edgv.aux_reambulacao_l edgv.aux_reambulacao_p edgv.aux_revisao_a edgv.aux_revisao_l edgv.aux_revisao_p edgv.aux_validacao_a edgv.aux_validacao_l edgv.aux_validacao_p edgv.centroide_area_construida_p edgv.centroide_area_sem_dados_p edgv.centroide_elemento_hidrografico_p edgv.centroide_ilha_p edgv.centroide_limite_especial_p edgv.centroide_massa_dagua_p edgv.centroide_vegetacao_p edgv.cobter_area_construida_a edgv.cobter_massa_dagua_a edgv.cobter_vegetacao_a edgv.constr_area_uso_especifico_a edgv.constr_deposito_a edgv.constr_deposito_p edgv.constr_edificacao_a edgv.constr_edificacao_p edgv.constr_extracao_mineral_a edgv.constr_extracao_mineral_p edgv.constr_ocupacao_solo_a edgv.constr_ocupacao_solo_l edgv.constr_ocupacao_solo_p edgv.delimitador_area_construida_l edgv.delimitador_area_sem_dados_l edgv.delimitador_elemento_hidrografico_l edgv.delimitador_limite_especial_l edgv.delimitador_massa_dagua_l edgv.delimitador_vegetacao_l edgv.edicao_area_sem_dados_a edgv.edicao_borda_elemento_hidrografico_l edgv.edicao_grid_edicao_l edgv.edicao_identificador_trecho_rod_p edgv.edicao_limite_especial_l edgv.edicao_limite_legal_l edgv.edicao_ponto_mudanca_p edgv.edicao_simb_area_p edgv.edicao_simb_cota_mestra_l edgv.edicao_simb_direcao_corrente_p edgv.edicao_simb_torre_energia_p edgv.edicao_simb_vegetacao_p edgv.edicao_texto_generico_l edgv.edicao_texto_generico_p edgv.elemnat_curva_nivel_l edgv.elemnat_elemento_fisiografico_a edgv.elemnat_elemento_fisiografico_l edgv.elemnat_elemento_fisiografico_p edgv.elemnat_elemento_hidrografico_a edgv.elemnat_elemento_hidrografico_l edgv.elemnat_elemento_hidrografico_p edgv.elemnat_ilha_a edgv.elemnat_ilha_p edgv.elemnat_ponto_cotado_p edgv.elemnat_sumidouro_vertedouro_p edgv.elemnat_terreno_sujeito_inundacao_a edgv.elemnat_toponimo_fisiografico_natural_l edgv.elemnat_toponimo_fisiografico_natural_p edgv.elemnat_trecho_drenagem_l edgv.infra_alteracao_fisiografica_antropica_l edgv.infra_barragem_a edgv.infra_barragem_l edgv.infra_elemento_energia_a edgv.infra_elemento_energia_l edgv.infra_elemento_energia_p edgv.infra_elemento_infraestrutura_a edgv.infra_elemento_infraestrutura_l edgv.infra_elemento_infraestrutura_p edgv.infra_elemento_viario_l edgv.infra_elemento_viario_p edgv.infra_ferrovia_l edgv.infra_mobilidade_urbana_l edgv.infra_pista_pouso_a edgv.infra_pista_pouso_l edgv.infra_pista_pouso_p edgv.infra_travessia_hidroviaria_l edgv.infra_trecho_duto_l edgv.infra_vala_l edgv.infra_via_deslocamento_l edgv.llp_delimitacao_fisica_l edgv.llp_limite_especial_a edgv.llp_localidade_p edgv.llp_pais_a edgv.llp_ponto_controle_p edgv.llp_unidade_federacao_a

Readers:
- POSTGIS_1: POSTGIS from $(SourceDataset_POSTGIS)
- POSTGIS_2: POSTGIS from $(SourceDataset_POSTGIS_9)
- POSTGIS_3: POSTGIS from $(SourceDataset_POSTGIS_11)
- POSTGIS_4: POSTGIS from $(SourceDataset_POSTGIS_6)
- POSTGIS_5: POSTGIS from $(SourceDataset_POSTGIS_13)
- POSTGIS_7: POSTGIS from $(SourceDataset_POSTGIS_10)
- OGCGEOPACKAGE_1: OGCGEOPACKAGE from $(SourceDataset_OGCGEOPACKAGE)
- POSTGIS_8: POSTGIS from $(SourceDataset_POSTGIS_12)

Writers:
- POSTGIS_6: POSTGIS to $(DestDataset_POSTGIS)

Note: 100k
aux_insumo_externo_a (reader POSTGIS_2)
    attributes: id uuid, nome varchar(255), fonte varchar(255), observacao varchar(255), operador_criacao varchar(255), data_criacao timestamptz, operador_atualizacao varchar(255), data_atualizacao timestamptz, administracao int2, altitude float4, altitude_geometrica varchar(255), altitude_ortometrica varchar(255), ancora_horizontal int2, ancora_vertical int2, assentamento_precario int2, bitola int2, canteiro_divisorio int2, cod_ponto varchar(255), concessionaria varchar(255), cor varchar(255), corrigido int2, cota int4, cota_comprovada int2, cota_mais_alta int2, densamente_edificada int2, dentro_de_massa_dagua int2, depressao int2, descricao varchar(255), desloc float4, direcao_fixada int2,
      eletrificada int2, em_arruamento int2, espacamento float4, estilo_fonte varchar(255), exibir_lado_simbologia int2, exibir_linha_rotulo int2, exibir_ponta_simbologia int2, exibir_rotulo_aproximado int2, finalidade int2, forma_extracao int2, geometria_aproximada int2, indice int2, inom varchar(255), jurisdicao int2, justificativa varchar(255), justificativa_txt int2, label_x float4, label_y float4, largura_simbologia float4, latitude varchar(255), longitude varchar(255), material_construcao int2, mi varchar(255), modal_uso int2, nr_faixas varchar(255), nr_linhas int2, nr_pistas varchar(255), ordem_simbologia int4, orgao_responsavel varchar(255), populacao int4,
      posicao_pista int2, posicao_relativa int2, posicao_rotulo int2, referencial_altim int2, referencial_grav int2, regime int2, revestimento int2, sigla varchar(255), simb_rot float4, sistema_geodesico int2, situacao_em_poligono int2, situacao_fisica int2, situacao_marco int2, sobreposto int2, sobreposto_transportes int2, subfase_id int4, sujeito_inundacao int2, suprimir_bandeira int2, suprimir_simbologia int2, tamanho_txt float4, texto_edicao varchar(255), tipo int2, tipo_exposicao int2, tipo_produto int2, tipo_ref int2, trafego int2, uso_pista int2, visivel int2
    -> val_14 [Deaggregator_2_Input]
val_14
    Deaggregator_3_Deaggregated -> Clipper_10 [CANDIDATE]
aux_insumo_externo_a (reader POSTGIS_8)
    attributes: id uuid, nome varchar(255), fonte varchar(255), observacao varchar(255), operador_criacao varchar(255), data_criacao timestamptz, operador_atualizacao varchar(255), data_atualizacao timestamptz, administracao int2, altitude float4, altitude_geometrica varchar(255), altitude_ortometrica varchar(255), ancora_horizontal int2, ancora_vertical int2, assentamento_precario int2, bitola int2, canteiro_divisorio int2, cod_ponto varchar(255), concessionaria varchar(255), cor varchar(255), corrigido int2, cota int4, cota_comprovada int2, cota_mais_alta int2, densamente_edificada int2, dentro_de_massa_dagua int2, depressao int2, descricao varchar(255), desloc float4, direcao_fixada int2,
      eletrificada int2, em_arruamento int2, espacamento float4, estilo_fonte varchar(255), exibir_lado_simbologia int2, exibir_linha_rotulo int2, exibir_ponta_simbologia int2, exibir_rotulo_aproximado int2, finalidade int2, forma_extracao int2, geometria_aproximada int2, indice int2, inom varchar(255), jurisdicao int2, justificativa varchar(255), justificativa_txt int2, label_x float4, label_y float4, largura_simbologia float4, latitude varchar(255), longitude varchar(255), material_construcao int2, mi varchar(255), modal_uso int2, nr_faixas varchar(255), nr_linhas int2, nr_pistas varchar(255), ordem_simbologia int4, orgao_responsavel varchar(255), populacao int4,
      posicao_pista int2, posicao_relativa int2, posicao_rotulo int2, referencial_altim int2, referencial_grav int2, regime int2, revestimento int2, sigla varchar(255), simb_rot float4, sistema_geodesico int2, situacao_em_poligono int2, situacao_fisica int2, situacao_marco int2, sobreposto int2, sobreposto_transportes int2, subfase_id int4, sujeito_inundacao int2, suprimir_bandeira int2, suprimir_simbologia int2, tamanho_txt float4, texto_edicao varchar(255), tipo int2, tipo_exposicao int2, tipo_produto int2, tipo_ref int2, trafego int2, uso_pista int2, visivel int2
    -> val_11 [Deaggregator_2_Input]
Note: 10k
aux_insumo_externo_a (reader POSTGIS_5)
    attributes: id uuid, nome varchar(255), fonte varchar(255), observacao varchar(255), operador_criacao varchar(255), data_criacao timestamptz, operador_atualizacao varchar(255), data_atualizacao timestamptz, administracao int2, altitude float4, altitude_geometrica varchar(255), altitude_ortometrica varchar(255), ancora_horizontal int2, ancora_vertical int2, assentamento_precario int2, bitola int2, canteiro_divisorio int2, cod_ponto varchar(255), concessionaria varchar(255), cor varchar(255), corrigido int2, cota int4, cota_comprovada int2, cota_mais_alta int2, densamente_edificada int2, dentro_de_massa_dagua int2, depressao int2, descricao varchar(255), desloc float4, direcao_fixada int2,
      eletrificada int2, em_arruamento int2, espacamento float4, estilo_fonte varchar(255), exibir_lado_simbologia int2, exibir_linha_rotulo int2, exibir_ponta_simbologia int2, exibir_rotulo_aproximado int2, finalidade int2, forma_extracao int2, geometria_aproximada int2, indice int2, inom varchar(255), jurisdicao int2, justificativa varchar(255), justificativa_txt int2, label_x float4, label_y float4, largura_simbologia float4, latitude varchar(255), longitude varchar(255), material_construcao int2, mi varchar(255), modal_uso int2, nr_faixas varchar(255), nr_linhas int2, nr_pistas varchar(255), ordem_simbologia int4, orgao_responsavel varchar(255), populacao int4,
      posicao_pista int2, posicao_relativa int2, posicao_rotulo int2, referencial_altim int2, referencial_grav int2, regime int2, revestimento int2, sigla varchar(255), simb_rot float4, sistema_geodesico int2, situacao_em_poligono int2, situacao_fisica int2, situacao_marco int2, sobreposto int2, sobreposto_transportes int2, subfase_id int4, sujeito_inundacao int2, suprimir_bandeira int2, suprimir_simbologia int2, tamanho_txt float4, texto_edicao varchar(255), tipo int2, tipo_exposicao int2, tipo_produto int2, tipo_ref int2, trafego int2, uso_pista int2, visivel int2
    -> val_10 [Deaggregator_2_Input]
val_10
    Deaggregator_3_Deaggregated -> Clipper_13 [CANDIDATE]
Note: 50k
aux_insumo_externo_a (reader POSTGIS_3)
    attributes: id uuid, nome varchar(255), fonte varchar(255), observacao varchar(255), operador_criacao varchar(255), data_criacao timestamptz, operador_atualizacao varchar(255), data_atualizacao timestamptz, administracao int2, altitude float4, altitude_geometrica varchar(255), altitude_ortometrica varchar(255), ancora_horizontal int2, ancora_vertical int2, assentamento_precario int2, bitola int2, canteiro_divisorio int2, cod_ponto varchar(255), concessionaria varchar(255), cor varchar(255), corrigido int2, cota int4, cota_comprovada int2, cota_mais_alta int2, densamente_edificada int2, dentro_de_massa_dagua int2, depressao int2, descricao varchar(255), desloc float4, direcao_fixada int2,
      eletrificada int2, em_arruamento int2, espacamento float4, estilo_fonte varchar(255), exibir_lado_simbologia int2, exibir_linha_rotulo int2, exibir_ponta_simbologia int2, exibir_rotulo_aproximado int2, finalidade int2, forma_extracao int2, geometria_aproximada int2, indice int2, inom varchar(255), jurisdicao int2, justificativa varchar(255), justificativa_txt int2, label_x float4, label_y float4, largura_simbologia float4, latitude varchar(255), longitude varchar(255), material_construcao int2, mi varchar(255), modal_uso int2, nr_faixas varchar(255), nr_linhas int2, nr_pistas varchar(255), ordem_simbologia int4, orgao_responsavel varchar(255), populacao int4,
      posicao_pista int2, posicao_relativa int2, posicao_rotulo int2, referencial_altim int2, referencial_grav int2, regime int2, revestimento int2, sigla varchar(255), simb_rot float4, sistema_geodesico int2, situacao_em_poligono int2, situacao_fisica int2, situacao_marco int2, sobreposto int2, sobreposto_transportes int2, subfase_id int4, sujeito_inundacao int2, suprimir_bandeira int2, suprimir_simbologia int2, tamanho_txt float4, texto_edicao varchar(255), tipo int2, tipo_exposicao int2, tipo_produto int2, tipo_ref int2, trafego int2, uso_pista int2, visivel int2
    -> val_13 [Deaggregator_2_Input]
val_13
    Deaggregator_3_Deaggregated -> Clipper_11 [CANDIDATE]
Note: 25k
aux_insumo_externo_a (reader POSTGIS_4)
    attributes: id uuid, nome varchar(255), fonte varchar(255), observacao varchar(255), operador_criacao varchar(255), data_criacao timestamptz, operador_atualizacao varchar(255), data_atualizacao timestamptz, administracao int2, altitude float4, altitude_geometrica varchar(255), altitude_ortometrica varchar(255), ancora_horizontal int2, ancora_vertical int2, assentamento_precario int2, bitola int2, canteiro_divisorio int2, cod_ponto varchar(255), concessionaria varchar(255), cor varchar(255), corrigido int2, cota int4, cota_comprovada int2, cota_mais_alta int2, densamente_edificada int2, dentro_de_massa_dagua int2, depressao int2, descricao varchar(255), desloc float4, direcao_fixada int2,
      eletrificada int2, em_arruamento int2, espacamento float4, estilo_fonte varchar(255), exibir_lado_simbologia int2, exibir_linha_rotulo int2, exibir_ponta_simbologia int2, exibir_rotulo_aproximado int2, finalidade int2, forma_extracao int2, geometria_aproximada int2, indice int2, inom varchar(255), jurisdicao int2, justificativa varchar(255), justificativa_txt int2, label_x float4, label_y float4, largura_simbologia float4, latitude varchar(255), longitude varchar(255), material_construcao int2, mi varchar(255), modal_uso int2, nr_faixas varchar(255), nr_linhas int2, nr_pistas varchar(255), ordem_simbologia int4, orgao_responsavel varchar(255), populacao int4,
      posicao_pista int2, posicao_relativa int2, posicao_rotulo int2, referencial_altim int2, referencial_grav int2, regime int2, revestimento int2, sigla varchar(255), simb_rot float4, sistema_geodesico int2, situacao_em_poligono int2, situacao_fisica int2, situacao_marco int2, sobreposto int2, sobreposto_transportes int2, subfase_id int4, sujeito_inundacao int2, suprimir_bandeira int2, suprimir_simbologia int2, tamanho_txt float4, texto_edicao varchar(255), tipo int2, tipo_exposicao int2, tipo_produto int2, tipo_ref int2, trafego int2, uso_pista int2, visivel int2
    -> val_11 [Deaggregator_2_Input]
val_11
    Deaggregator_3_Deaggregated -> Clipper_12 [CANDIDATE]
moldura_100k (reader OGCGEOPACKAGE_1)
    attributes: id text, nome text(255), mi text(255), inom text(255), observacao text(255), operador_criacao text(255), data_criacao datetime, operador_atualizacao text(255), data_atualizacao datetime, area_otf double, fid int,PrimaryKey
    -> Clipper_10 [CLIPPER]
    -> Clipper_11 [CLIPPER]
    -> Clipper_12 [CLIPPER]
    -> Clipper_13 [CLIPPER]
Clipper_10
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> val_4 [Deaggregator_2_Input]
val_4
    Deaggregator_3_Deaggregated -> Tester_3
Tester_3
    BOOL_OP = OR
    TEST_CLAUSE = TEST @Value(fme_feature_type) = edgv.aux_moldura_a
    TEST_MODE = TEST
    PASSED -> Clipper_2 [CLIPPER]
    PASSED -> val_3 [Deaggregator_2_Input]
    PASSED -> Clipper_3 [CLIPPER]
    FAILED -> Clipper_2 [CANDIDATE]
Clipper_2
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> val_3 [Deaggregator_2_Input]
Clipper_11
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> val_6 [Deaggregator_2_Input]
val_6
    Deaggregator_3_Deaggregated -> Tester_5
Tester_5
    BOOL_OP = OR
    TEST_CLAUSE = TEST @Value(fme_feature_type) = edgv.aux_moldura_a
    TEST_MODE = TEST
    PASSED -> Clipper_4 [CLIPPER]
    PASSED -> val_5 [Deaggregator_2_Input]
    PASSED -> Clipper_5 [CLIPPER]
    FAILED -> Clipper_4 [CANDIDATE]
Clipper_4
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> val_5 [Deaggregator_2_Input]
Clipper_12
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> val_8 [Deaggregator_2_Input]
val_8
    Deaggregator_3_Deaggregated -> Tester_6
Tester_6
    BOOL_OP = OR
    TEST_CLAUSE = TEST @Value(fme_feature_type) = edgv.aux_moldura_a
    TEST_MODE = TEST
    PASSED -> Dissolver
    FAILED -> Clipper_6 [CANDIDATE]
Dissolver
    ACCUM_INPUT_ATTRS = Use Attributes From One Feature
    CLEANING_TOLERANCE = Automatic
    CONNECT_Z_MODE = First Wins
    DEAGGREGATE_INPUT = Yes
    AREA -> Clipper_6 [CLIPPER]
    AREA -> val_7 [Deaggregator_2_Input]
    AREA -> Clipper_7 [CLIPPER]
Clipper_6
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> val_7 [Deaggregator_2_Input]
Clipper_13
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> val_12 [Deaggregator_2_Input]
val_12
    Deaggregator_3_Deaggregated -> Tester_7
Tester_7
    BOOL_OP = OR
    TEST_CLAUSE = TEST @Value(fme_feature_type) = edgv.aux_moldura_a
    TEST_MODE = TEST
    PASSED -> Clipper_8 [CLIPPER]
    PASSED -> val_9 [Deaggregator_2_Input]
    PASSED -> Clipper_9 [CLIPPER]
    FAILED -> Clipper_8 [CANDIDATE]
Clipper_8
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> val_9 [Deaggregator_2_Input]
Note: multiescala
aux_insumo_externo_100k_a (reader POSTGIS_7)
    attributes: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
Note: 250k
aux_insumo_externo_a (reader POSTGIS_1) [off]
    attributes: id uuid, nome varchar(255), fonte varchar(255), observacao varchar(255), operador_criacao varchar(255), data_criacao timestamptz, operador_atualizacao varchar(255), data_atualizacao timestamptz, administracao int2, altitude float4, altitude_geometrica varchar(255), altitude_ortometrica varchar(255), ancora_horizontal int2, ancora_vertical int2, assentamento_precario int2, bitola int2, canteiro_divisorio int2, cod_ponto varchar(255), concessionaria varchar(255), cor varchar(255), corrigido int2, cota int4, cota_comprovada int2, cota_mais_alta int2, densamente_edificada int2, dentro_de_massa_dagua int2, depressao int2, descricao varchar(255), desloc float4, direcao_fixada int2,
      eletrificada int2, em_arruamento int2, espacamento float4, estilo_fonte varchar(255), exibir_lado_simbologia int2, exibir_linha_rotulo int2, exibir_ponta_simbologia int2, exibir_rotulo_aproximado int2, finalidade int2, forma_extracao int2, geometria_aproximada int2, indice int2, inom varchar(255), jurisdicao int2, justificativa varchar(255), justificativa_txt int2, label_x float4, label_y float4, largura_simbologia float4, latitude varchar(255), longitude varchar(255), material_construcao int2, mi varchar(255), modal_uso int2, nr_faixas varchar(255), nr_linhas int2, nr_pistas varchar(255), ordem_simbologia int4, orgao_responsavel varchar(255), populacao int4,
      posicao_pista int2, posicao_relativa int2, posicao_rotulo int2, referencial_altim int2, referencial_grav int2, regime int2, revestimento int2, sigla varchar(255), simb_rot float4, sistema_geodesico int2, situacao_em_poligono int2, situacao_fisica int2, situacao_marco int2, sobreposto int2, sobreposto_transportes int2, subfase_id int4, sujeito_inundacao int2, suprimir_bandeira int2, suprimir_simbologia int2, tamanho_txt float4, texto_edicao varchar(255), tipo int2, tipo_exposicao int2, tipo_produto int2, tipo_ref int2, trafego int2, uso_pista int2, visivel int2
    -> val_2 [Deaggregator_2_Input]
val_2 [off]
    Deaggregator_3_Deaggregated -> Tester
Tester [off]
    BOOL_OP = OR
    TEST_CLAUSE = TEST @Value(fme_feature_type) = edgv.aux_moldura_a
    TEST_MODE = TEST
    PASSED -> Clipper [CLIPPER]
    PASSED -> val [Deaggregator_2_Input]
    PASSED -> val_3 [Deaggregator_2_Input]
    FAILED -> Clipper [CANDIDATE]
Clipper [off]
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> val [Deaggregator_2_Input]
val [off]
    Deaggregator_3_Deaggregated -> Clipper_3 [CANDIDATE]
Clipper_3
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> val_3 [Deaggregator_2_Input]
val_3
    Deaggregator_3_Deaggregated -> Clipper_5 [CANDIDATE]
Clipper_5
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> val_5 [Deaggregator_2_Input]
val_5
    Deaggregator_3_Deaggregated -> Clipper_7 [CANDIDATE]
Clipper_7
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> val_7 [Deaggregator_2_Input]
val_7
    Deaggregator_3_Deaggregated -> Clipper_9 [CANDIDATE]
Clipper_9
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> val_9 [Deaggregator_2_Input]
val_9
    Deaggregator_3_Deaggregated -> PythonCaller_EDGV3
Note: mapeamento
PythonCaller_EDGV3
    NEW_ATTRIBUTES = CLASS_NOT_FOUND INVALID_GEOM
    PYTHONSOURCE:
      import fme
      import fmeobjects
      import copy
      import sys
      import os
      import json

      class FeatureProcessor(object):
          def __init__(self):
              self.mappingDict = self.buildFileDict(FME_MacroValues['JsonMapeamento'])
              self.mappingType = FME_MacroValues['direcao']

          def buildFileDict(self, mappingPath):
              with open(mappingPath, 'r', encoding='utf-8') as file:
                  mapDict = json.loads(file.read())
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          if feature.getAttribute(attr) == 'f':
                              featDict[attr] = 'False'
                          elif feature.getAttribute(attr) == 't':
                              featDict[attr] = 'True'
                          else:
                              featDict[attr] = feature.getAttribute(attr)
                      else:
                          featDict[attr] = None
              if feature.performFunction('@GeometryType()') == 'fme_polygon' or feature.performFunction('@GeometryType()') == 'fme_donut':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              else:
                   featDict["INVALID_GEOM"] = True
              return featDict

          def evaluateExpression(self, featDict, expression):
              if not expression["nome_atributo"] in featDict:
                  return False
              if expression["valor"] is None or expression["valor"] == "":
                  return featDict[expression["nome_atributo"]] is None or featDict[expression["nome_atributo"]] == ""
              else:
                  return u"{0}".format(featDict[expression["nome_atributo"]]) == u"{0}".format(expression["valor"])

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "A=>B":
                  key_attr_origin = "attr_A"
                  key_attr_destiny = "attr_B"
                  key_value_origin = "valor_A"
                  key_value_destiny = "valor_B"
                  key_default = "atributos_default_B"
                  key_filter = "filtro_A"
                  key_class_origin = "classe_A"
                  key_class_destiny = "classe_B"
                  key_group_origin = "tupla_A"
                  key_group_destiny = "tupla_B"
                  key_affix_origin = "afixo_geom_A"
                  key_affix_destiny = "afixo_geom_B"
                  key_schema_origin = "schema_A"
                  key_schema_destiny = "schema_B"
                  key_class_affix_origin = "com_afixo_geom_A"
                  key_class_affix_destiny = "com_afixo_geom_B"
                  key_class_schema_origin = "com_schema_A"
                  key_class_schema_destiny = "com_schema_B"
                  key_agregar = "agregar_geom_A"
              else:
                  key_attr_origin = "attr_B"
                  key_attr_destiny = "attr_A"
                  key_value_origin = "valor_B"
                  key_value_destiny = "valor_A"
                  key_default = "atributos_default_A"
                  key_filter = "filtro_B"
                  key_class_origin = "classe_B"
                  key_class_destiny = "classe_A"
                  key_group_origin = "tupla_B"
                  key_group_destiny = "tupla_A"
                  key_affix_origin = "afixo_geom_B"
                  key_affix_destiny = "afixo_geom_A"
                  key_schema_origin = "schema_B"
                  key_schema_destiny = "schema_A"
                  key_class_affix_origin = "com_afixo_geom_B"
                  key_class_affix_destiny = "com_afixo_geom_A"
                  key_class_schema_origin = "com_schema_B"
                  key_class_schema_destiny = "com_schema_A"
                  key_agregar = "agregar_geom_B"

              featDict["fme_feature_type_original"] = featDict["fme_feature_type"]

              if key_schema_origin in self.mappingDict and self.mappingDict[key_schema_origin]:
                  featDict["fme_feature_type"] = featDict["fme_feature_type"][len(self.mappingDict[key_schema_origin])+1:]

              featDict["fme_feature_type_sem_schema"] = featDict["fme_feature_type"]

              if key_affix_origin in self.mappingDict and 'tipo' in self.mappingDict[key_affix_origin] and self.mappingDict[key_affix_origin]['tipo'] == 'sufixo':
                  featDict["fme_feature_type"] = featDict["fme_feature_type"][:-len(self.mappingDict[key_affix_origin][featDict["$GEOM_TYPE"]])]
                  featDict["fme_feature_type_sem_afixo"] = featDict["fme_feature_type_original"][:-len(self.mappingDict[key_affix_origin][featDict["$GEOM_TYPE"]])]

              if key_affix_origin in self.mappingDict and 'tipo' in self.mappingDict[key_affix_origin] and self.mappingDict[key_affix_origin]['tipo'] == 'prefixo':
                  featDict["fme_feature_type"] = featDict["fme_feature_type"][len(self.mappingDict[key_affix_origin][featDict["$GEOM_TYPE"]]):]
                  featDict["fme_feature_type_sem_afixo"] = featDict["fme_feature_type_original"][len(self.mappingDict[key_affix_origin][featDict["$GEOM_TYPE"]]):]

              should_map = False
              for classmap in self.mappingDict['mapeamento_classes']:
                  if "sentido" not in classmap or ("sentido" in classmap and classmap["sentido"] == self.mappingType):
                      if key_class_affix_origin in classmap and classmap[key_class_affix_origin] and key_class_schema_origin in classmap and classmap[key_class_schema_origin]:
                          class_name = featDict["fme_feature_type_original"]
                      elif key_class_affix_origin in classmap and classmap[key_class_affix_origin]:
                          class_name = featDict["fme_feature_type_sem_schema"]
                      elif key_class_schema_origin in classmap and classmap[key_class_schema_origin]:
                          class_name = featDict["fme_feature_type_sem_afixo"]
                      else:
                           class_name = featDict["fme_feature_type"]

                      if classmap[key_class_origin] == class_name:
                          if key_filter in classmap:
                              if not self.evaluateFilter(featDict, classmap[key_filter]):
                                  continue
                          should_map = True
              if not should_map:
                  featDict["CLASS_NOT_FOUND"] = True
                  return featDict

              mappedFeat = copy.deepcopy(featDict)

              if key_default in self.mappingDict:
                  for default in self.mappingDict[key_default]:
                      mappedFeat[default["nome_atributo"]] = default["valor"]

              if 'mapeamento_atributos' in self.mappingDict:
                  for attmap in self.mappingDict['mapeamento_atributos']:
                      if attmap[key_attr_origin] in mappedFeat:
                          mappedFeat[attmap[key_attr_destiny]] = featDict[attmap[key_attr_origin]]
                          if "traducao" in attmap:
                              for valuemap in attmap["traducao"]:
                                  if u"{0}".format(valuemap[key_value_origin]) == u"{0}".format(featDict[attmap[key_attr_origin]]) and ("sentido" not in valuemap or ("sentido" in valuemap and valuemap["sentido"] == self.mappingType)):
                                      mappedFeat[attmap[key_attr_destiny]] = valuemap[key_value_destiny]

              if "mapeamento_multiplo" in self.mappingDict:
                  for attmap in self.mappingDict['mapeamento_multiplo']:
                      if "sentido" not in attmap or ("sentido" in attmap and attmap["sentido"] == self.mappingType):
                          if all([self.evaluateExpression(featDict, condition) for condition in attmap[key_group_origin]]):
                              for valuemap in attmap[key_group_destiny]:
                                  if "concatenar" in valuemap and valuemap["concatenar"] and valuemap["nome_atributo"] in mappedFeat and mappedFeat[valuemap["nome_atributo"]]:
                                      mappedFeat[valuemap["nome_atributo"]] = mappedFeat[valuemap["nome_atributo"]] + ' | ' + valuemap["valor"]
                                  else:
                                      mappedFeat[valuemap["nome_atributo"]] = valuemap["valor"]

              if 'mapeamento_classes' in self.mappingDict:
                  for classmap in self.mappingDict['mapeamento_classes']:
                      if "sentido" not in classmap or ("sentido" in classmap and classmap["sentido"] == self.mappingType):
                          if key_class_affix_origin in classmap and classmap[key_class_affix_origin] and key_class_schema_origin in classmap and classmap[key_class_schema_origin]:
                              class_name = featDict["fme_feature_type_original"]
                          elif key_class_affix_origin in classmap and classmap[key_class_affix_origin]:
                              class_name = featDict["fme_feature_type_sem_schema"]
                          elif key_class_schema_origin in classmap and classmap[key_class_schema_origin]:
                              class_name = featDict["fme_feature_type_sem_afixo"]
                          else:
                              class_name = featDict["fme_feature_type"]

                          if classmap[key_class_origin] == class_name:
                              if key_filter in classmap:
                                  if not self.evaluateFilter(featDict, classmap[key_filter]):
                                      continue

                              mappedFeat["fme_feature_type"] = classmap[key_class_destiny]

                              if key_class_affix_destiny in classmap and classmap[key_class_affix_destiny]:
                                  pass
                              elif key_affix_destiny in self.mappingDict and 'tipo' in self.mappingDict[key_affix_destiny]:
                                  if self.mappingDict[key_affix_destiny]['tipo'] == 'sufixo':
                                      mappedFeat["fme_feature_type"] = mappedFeat["fme_feature_type"] + self.mappingDict[key_affix_destiny][featDict["$GEOM_TYPE"]]

                                  if self.mappingDict[key_affix_destiny]['tipo'] == 'prefixo':
                                      mappedFeat["fme_feature_type"] = self.mappingDict[key_affix_destiny][featDict["$GEOM_TYPE"]] + mappedFeat["fme_feature_type"]

                              if key_class_schema_destiny in classmap and classmap[key_class_schema_destiny]:
                                  pass
                              elif key_schema_destiny in self.mappingDict and self.mappingDict[key_schema_destiny]:
                                  mappedFeat["fme_feature_type"] = self.mappingDict[key_schema_destiny] + '.' + mappedFeat["fme_feature_type"]


                              if key_default in classmap:
                                  for default in classmap[key_default]:
                                      mappedFeat[default["nome_atributo"]] = default["valor"]

                              if "mapeamento_atributos" in classmap:
                                  for attmap in classmap['mapeamento_atributos']:
                                      if attmap[key_attr_origin] in featDict:
                                          if attmap[key_attr_destiny] not in mappedFeat:
                                              mappedFeat[attmap[key_attr_destiny]] = featDict[attmap[key_attr_origin]]
                                          if "traducao" in attmap:
                                              for valuemap in attmap["traducao"]:
                                                  if u"{0}".format(valuemap[key_value_origin]) == u"{0}".format(featDict[attmap[key_attr_origin]]) and ("sentido" not in valuemap or ("sentido" in valuemap and valuemap["sentido"] == self.mappingType)):
                                                      mappedFeat[attmap[key_attr_destiny]] = valuemap[key_value_destiny]

                              if "mapeamento_multiplo" in classmap:
                                  for attmap in classmap['mapeamento_multiplo']:
                                      if "sentido" not in attmap or ("sentido" in attmap and attmap["sentido"] == self.mappingType):
                                          if all([self.evaluateExpression(featDict, condition) for condition in attmap[key_group_origin]]):
                                              for valuemap in attmap[key_group_destiny]:
                                                  if "concatenar" in valuemap and valuemap["concatenar"] and valuemap["nome_atributo"] in mappedFeat and mappedFeat[valuemap["nome_atributo"]]:
                                                      mappedFeat[valuemap["nome_atributo"]] = mappedFeat[valuemap["nome_atributo"]] + ' | ' + valuemap["valor"]
                                                  else:
                                                      mappedFeat[valuemap["nome_atributo"]] = valuemap["valor"]

                              if key_agregar in classmap:
                                  mappedFeat["AGGREGATE_GEOM"] = classmap[key_agregar]
                              elif key_agregar in self.mappingDict:
                                  mappedFeat["AGGREGATE_GEOM"] = self.mappingDict[key_agregar]

                              break

              return mappedFeat

          def mapDictToFeature(self, feat, featDict):
              for attr, value in featDict.items():
                  if value == 'True':
                      feat.setAttribute(attr, 1)
                  elif value == 'False':
                      feat.setAttribute(attr, 0)
                  elif value or value == 0:
                      feat.setAttribute(attr, u'{0}'.format(value))
                  else:
                      feat.setAttributeNullWithType(attr,0)
              if "AGGREGATE_GEOM" in featDict and featDict["AGGREGATE_GEOM"]:
                  feat.buildAggregateFeat([feat])
              return feat

          def input(self,feature):
              if feature.performFunction('@GeometryType()') == 'fme_aggregate':
                  features = feature.splitAggregate(True)
              else:
                  features = [feature]
              for simple_feature in features:
                  feat = self.buildFeatureDict(simple_feature)
                  if "INVALID_GEOM" in feat and feat["INVALID_GEOM"]:
                      simple_feature.setAttribute("INVALID_GEOM", u'True')
                      self.pyoutput(simple_feature)
                      continue

                  outputFeatDict = self.convertFeature(feat)
                  if "CLASS_NOT_FOUND" in outputFeatDict and not outputFeatDict["CLASS_NOT_FOUND"]:
                      simple_feature.setAttribute("CLASS_NOT_FOUND", u'True')
                      self.pyoutput(simple_feature)
                  else:
                      outputFeature = self.mapDictToFeature(simple_feature, outputFeatDict)
                      self.pyoutput(outputFeature)

          def close(self):
              pass
    PYTHONSYMBOL = FeatureProcessor
    -> Tester_2
Note: Teste de invalid geom
Tester_2
    BOOL_OP = OR
    TEST_CLAUSE = TEST @Value(INVALID_GEOM) = True
    TEST_MODE = TEST
    PASSED -> Tester_2_Passed
    FAILED -> Tester_4
Tester_2_Passed: Inspector
Note: Teste de mapeamento
Tester_4
    BOOL_OP = OR
    TEST_CLAUSE = TEST @Value(CLASS_NOT_FOUND) = True
    TEST_MODE = TEST
    PASSED -> DuplicateFilter
    FAILED -> UniqueIdentifierGenerator
DuplicateFilter
    INPUT_ORDERED_CHOICE = No
    KEYATTR = fme_feature_type
    UNIQUE -> CLASS_NOT_FOUND
CLASS_NOT_FOUND: Inspector
UniqueIdentifierGenerator
    UUID_ATTR = id
    UUID_FORMAT = UUID_ONLY
    -> Table1 (writer POSTGIS_6)
Table1 (writer POSTGIS_6)

FME custom transformer val

Deaggregator_2_Input (input)
    -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryValidator
GeometryValidator
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK OGC_SIMPLE_CHECK LEGACY_OGC]No]FME_CONTROLLER_QUERY_FILE]transformers/dependencies/geometryvalidator8/OGC_SIMPLE_CHECK.fme]FME_CONTROLLER_CHOICE]OGC_SIMPLE_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> Deaggregator_3
    FAILED -> Deaggregator_3
    REPAIRED -> Deaggregator_3
Deaggregator_3
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryFilter
GeometryFilter
    FILTER_MODE = SIMPLE
    FILTER_MULTI = FILTER_TYPES]"Point Line Area"]FME_CONTROLLER_QUERY_FILE]]FME_CONTROLLER_CHOICE]Simple
    Point -> Deaggregator_3_Deaggregated (output)
    Curve -> Deaggregator_3_Deaggregated (output)
    Area -> Deaggregator_3_Deaggregated (output)
Deaggregator_3_Deaggregated (output)
