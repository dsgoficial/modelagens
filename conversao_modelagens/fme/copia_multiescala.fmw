FME workspace copia_multiescala.fmw

Parameters:
- JsonMapeamento = C:\Diniz\modelagens\conversao_modelagens\arquivos_mapeamento\conversao_pg-edgv-300topo14_pg-edgv-300topo-multiescala14.json   # Arquivo de mapeamento
- direcao = A=>B   # Direção do mapeamento
- SourceDataset_POSTGIS_9 = asc_sc_pr_250k_4674_edgv30pro   # Database
- FEATURE_TYPES_2 = edgv.aux_insumo_externo_a edgv.aux_insumo_externo_l edgv.aux_insumo_externo_p edgv.aux_moldura_a edgv.aux_moldura_area_continua_a edgv.aux_reambulacao_a edgv.aux_reambulacao_l edgv.aux_reambulacao_p edgv.aux_revisao_a edgv.aux_revisao_l edgv.aux_revisao_p edgv.aux_validacao_a edgv.aux_validacao_l edgv.aux_validacao_p edgv.centroide_area_construida_p edgv.centroide_area_sem_dados_p edgv.centroide_elemento_hidrografico_p edgv.centroide_ilha_p edgv.centroide_limite_especial_p edgv.centroide_massa_dagua_p edgv.centroide_vegetacao_p edgv.cobter_area_construida_a edgv.cobter_massa_dagua_a edgv.cobter_vegetacao_a edgv.constr_area_uso_especifico_a edgv.constr_deposito_a edgv.constr_deposito_p edgv.constr_edificacao_a edgv.constr_edificacao_p edgv.constr_extracao_mineral_a edgv.constr_extracao_mineral_p edgv.constr_ocupacao_solo_a edgv.constr_ocupacao_solo_l edgv.constr_ocupacao_solo_p edgv.delimitador_area_construida_l edgv.delimitador_area_sem_dados_l edgv.delimitador_elemento_hidrografico_l edgv.delimitador_limite_especial_l edgv.delimitador_massa_dagua_l edgv.delimitador_vegetacao_l edgv.edicao_area_sem_dados_a edgv.edicao_borda_elemento_hidrografico_l edgv.edicao_identificador_trecho_rod_p edgv.edicao_limite_especial_l edgv.edicao_limite_legal_l edgv.edicao_simb_area_p edgv.edicao_simb_cota_mestra_l edgv.edicao_simb_direcao_corrente_p edgv.edicao_simb_torre_energia_p edgv.edicao_simb_vegetacao_p edgv.edicao_texto_generico_l edgv.edicao_texto_generico_p edgv.elemnat_curva_nivel_l edgv.elemnat_elemento_fisiografico_a edgv.elemnat_elemento_fisiografico_l edgv.elemnat_elemento_fisiografico_p edgv.elemnat_elemento_hidrografico_a edgv.elemnat_elemento_hidrografico_l edgv.elemnat_elemento_hidrografico_p edgv.elemnat_ilha_a edgv.elemnat_ilha_p edgv.elemnat_ponto_cotado_p edgv.elemnat_sumidouro_vertedouro_p edgv.elemnat_terreno_sujeito_inundacao_a edgv.elemnat_toponimo_fisiografico_natural_l edgv.elemnat_toponimo_fisiografico_natural_p edgv.elemnat_trecho_drenagem_l edgv.infra_alteracao_fisiografica_antropica_l edgv.infra_barragem_a edgv.infra_barragem_l edgv.infra_elemento_energia_a edgv.infra_elemento_energia_l edgv.infra_elemento_energia_p edgv.infra_elemento_infraestrutura_a edgv.infra_elemento_infraestrutura_l edgv.infra_elemento_infraestrutura_p edgv.infra_elemento_viario_l edgv.infra_elemento_viario_p edgv.infra_ferrovia_l edgv.infra_mobilidade_urbana_l edgv.infra_pista_pouso_a edgv.infra_pista_pouso_l edgv.infra_pista_pouso_p edgv.infra_travessia_hidroviaria_l edgv.infra_trecho_duto_l edgv.infra_vala_l edgv.infra_via_deslocamento_l edgv.llp_delimitacao_fisica_l edgv.llp_limite_especial_a edgv.llp_localidade_p edgv.llp_pais_a edgv.llp_ponto_controle_p edgv.llp_unidade_federacao_a
- DestDataset_POSTGIS = asc_multiescala_4674_edgvtopo14multi   # Database
- SourceDataset_POSTGIS_10 = asc_multiescala_4674_edgvtopo14multi   # Database
- FEATURE_TYPES_6 =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

Readers:
- POSTGIS_2: POSTGIS from $(SourceDataset_POSTGIS_9)
- POSTGIS_7: POSTGIS from $(SourceDataset_POSTGIS_10)

Writers:
- POSTGIS_6: POSTGIS to $(DestDataset_POSTGIS)

aux_insumo_externo_a (reader POSTGIS_2)
    attributes: id uuid, nome varchar(255), fonte varchar(255), observacao varchar(255), operador_criacao varchar(255), data_criacao timestamptz, operador_atualizacao varchar(255), data_atualizacao timestamptz, administracao int2, altitude float4, altitude_geometrica varchar(255), altitude_ortometrica varchar(255), ancora_horizontal int2, ancora_vertical int2, assentamento_precario int2, bitola int2, canteiro_divisorio int2, cod_ponto varchar(255), concessionaria varchar(255), cor varchar(255), corrigido int2, cota int4, cota_comprovada int2, cota_mais_alta int2, densamente_edificada int2, dentro_de_massa_dagua int2, depressao int2, descricao varchar(255), desloc float4, direcao_fixada int2,
      eletrificada int2, em_arruamento int2, espacamento float4, estilo_fonte varchar(255), exibir_lado_simbologia int2, exibir_linha_rotulo int2, exibir_ponta_simbologia int2, exibir_rotulo_aproximado int2, finalidade int2, forma_extracao int2, geometria_aproximada int2, indice int2, inom varchar(255), jurisdicao int2, justificativa varchar(255), justificativa_txt int2, label_x float4, label_y float4, largura_simbologia float4, latitude varchar(255), longitude varchar(255), material_construcao int2, mi varchar(255), modal_uso int2, nr_faixas varchar(255), nr_linhas int2, nr_pistas varchar(255), ordem_simbologia int4, orgao_responsavel varchar(255), populacao int4,
      posicao_pista int2, posicao_relativa int2, posicao_rotulo int2, referencial_altim int2, referencial_grav int2, regime int2, revestimento int2, sigla varchar(255), simb_rot float4, sistema_geodesico int2, situacao_em_poligono int2, situacao_fisica int2, situacao_marco int2, sobreposto int2, sobreposto_transportes int2, subfase_id int4, sujeito_inundacao int2, suprimir_bandeira int2, suprimir_simbologia int2, tamanho_txt float4, texto_edicao varchar(255), tipo int2, tipo_exposicao int2, tipo_produto int2, tipo_ref int2, trafego int2, uso_pista int2, visivel int2
    -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryValidator
GeometryValidator
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK OGC_SIMPLE_CHECK LEGACY_OGC]No]FME_CONTROLLER_QUERY_FILE]transformers/dependencies/geometryvalidator8/OGC_SIMPLE_CHECK.fme]FME_CONTROLLER_CHOICE]OGC_SIMPLE_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> Tester_7
    FAILED -> Tester_7
    REPAIRED -> Tester_7
Tester_7
    BOOL_OP = OR
    TEST_CLAUSE = TEST @Value(fme_feature_type) = edgv.aux_moldura_a
    TEST_MODE = TEST
    PASSED -> Clipper [CLIPPER]
    PASSED -> Deaggregator_3
    FAILED -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Deaggregator_3
Deaggregator_3
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryValidator_2
GeometryValidator_2
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK OGC_SIMPLE_CHECK LEGACY_OGC]No]FME_CONTROLLER_QUERY_FILE]transformers/dependencies/geometryvalidator8/OGC_SIMPLE_CHECK.fme]FME_CONTROLLER_CHOICE]OGC_SIMPLE_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> Deaggregator_2
    FAILED -> Deaggregator_2
    REPAIRED -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Tester
Tester
    BOOL_OP = OR
    TEST_CLAUSE = CASE_INSENSITIVE_TEST @Value(fme_feature_type) ENDS_WITH _p
    TEST_MODE = TEST
    PASSED -> GeometryFilter
    FAILED -> Tester_3
GeometryFilter
    FILTER_MODE = SIMPLE
    FILTER_MULTI = FILTER_TYPES]"Point Line Area"]FME_CONTROLLER_QUERY_FILE]]FME_CONTROLLER_CHOICE]Simple
    Point -> Tester_6
Tester_3
    BOOL_OP = OR
    TEST_CLAUSE = CASE_INSENSITIVE_TEST @Value(fme_feature_type) ENDS_WITH _l
    TEST_MODE = CASE_INSENSITIVE_TEST
    PASSED -> GeometryFilter_2
    FAILED -> Tester_5
GeometryFilter_2
    FILTER_MODE = SIMPLE
    FILTER_MULTI = FILTER_TYPES]"Point Line Area"]FME_CONTROLLER_QUERY_FILE]]FME_CONTROLLER_CHOICE]Simple
    Curve -> Tester_6
Tester_5
    BOOL_OP = OR
    TEST_CLAUSE = CASE_INSENSITIVE_TEST @Value(fme_feature_type) ENDS_WITH _a
    TEST_MODE = CASE_INSENSITIVE_TEST
    PASSED -> GeometryFilter_3
    FAILED -> Tester_5_Failed
GeometryFilter_3
    FILTER_MODE = SIMPLE
    FILTER_MULTI = FILTER_TYPES]"Point Line Area"]FME_CONTROLLER_QUERY_FILE]]FME_CONTROLLER_CHOICE]Simple
    Area -> Tester_6
Tester_6
    BOOL_OP = OR
    TEST_CLAUSE = TEST @Value(fme_feature_type) != edgv.infra_elemento_viario_p
    TEST_MODE = TEST
    PASSED -> PythonCaller_EDGV3
Note: mapeamento
PythonCaller_EDGV3
    NEW_ATTRIBUTES = CLASS_NOT_FOUND INVALID_GEOM
    PYTHONSOURCE:
      import fme
      import fmeobjects
      import copy
      import sys
      import os
      import json

      class FeatureProcessor(object):
          def __init__(self):
              self.mappingDict = self.buildFileDict(FME_MacroValues['JsonMapeamento'])
              self.mappingType = FME_MacroValues['direcao']

          def buildFileDict(self, mappingPath):
              with open(mappingPath, 'r', encoding='utf-8') as file:
                  mapDict = json.loads(file.read())
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          if feature.getAttribute(attr) == 'f':
                              featDict[attr] = 'False'
                          elif feature.getAttribute(attr) == 't':
                              featDict[attr] = 'True'
                          else:
                              featDict[attr] = feature.getAttribute(attr)
                      else:
                          featDict[attr] = None
              if feature.performFunction('@GeometryType()') == 'fme_polygon' or feature.performFunction('@GeometryType()') == 'fme_donut':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              else:
                   featDict["INVALID_GEOM"] = True
              return featDict

          def evaluateExpression(self, featDict, expression):
              if not expression["nome_atributo"] in featDict:
                  return False
              if expression["valor"] is None or expression["valor"] == "":
                  return featDict[expression["nome_atributo"]] is None or featDict[expression["nome_atributo"]] == ""
              else:
                  return u"{0}".format(featDict[expression["nome_atributo"]]) == u"{0}".format(expression["valor"])

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "A=>B":
                  key_attr_origin = "attr_A"
                  key_attr_destiny = "attr_B"
                  key_value_origin = "valor_A"
                  key_value_destiny = "valor_B"
                  key_default = "atributos_default_B"
                  key_filter = "filtro_A"
                  key_class_origin = "classe_A"
                  key_class_destiny = "classe_B"
                  key_group_origin = "tupla_A"
                  key_group_destiny = "tupla_B"
                  key_affix_origin = "afixo_geom_A"
                  key_affix_destiny = "afixo_geom_B"
                  key_schema_origin = "schema_A"
                  key_schema_destiny = "schema_B"
                  key_class_affix_origin = "com_afixo_geom_A"
                  key_class_affix_destiny = "com_afixo_geom_B"
                  key_class_schema_origin = "com_schema_A"
                  key_class_schema_destiny = "com_schema_B"
                  key_agregar = "agregar_geom_A"
              else:
                  key_attr_origin = "attr_B"
                  key_attr_destiny = "attr_A"
                  key_value_origin = "valor_B"
                  key_value_destiny = "valor_A"
                  key_default = "atributos_default_A"
                  key_filter = "filtro_B"
                  key_class_origin = "classe_B"
                  key_class_destiny = "classe_A"
                  key_group_origin = "tupla_B"
                  key_group_destiny = "tupla_A"
                  key_affix_origin = "afixo_geom_B"
                  key_affix_destiny = "afixo_geom_A"
                  key_schema_origin = "schema_B"
                  key_schema_destiny = "schema_A"
                  key_class_affix_origin = "com_afixo_geom_B"
                  key_class_affix_destiny = "com_afixo_geom_A"
                  key_class_schema_origin = "com_schema_B"
                  key_class_schema_destiny = "com_schema_A"
                  key_agregar = "agregar_geom_B"

              featDict["fme_feature_type_original"] = featDict["fme_feature_type"]

              if key_schema_origin in self.mappingDict and self.mappingDict[key_schema_origin]:
                  featDict["fme_feature_type"] = featDict["fme_feature_type"][len(self.mappingDict[key_schema_origin])+1:]

              featDict["fme_feature_type_sem_schema"] = featDict["fme_feature_type"]

              if key_affix_origin in self.mappingDict and 'tipo' in self.mappingDict[key_affix_origin] and self.mappingDict[key_affix_origin]['tipo'] == 'sufixo':
                  featDict["fme_feature_type"] = featDict["fme_feature_type"][:-len(self.mappingDict[key_affix_origin][featDict["$GEOM_TYPE"]])]
                  featDict["fme_feature_type_sem_afixo"] = featDict["fme_feature_type_original"][:-len(self.mappingDict[key_affix_origin][featDict["$GEOM_TYPE"]])]

              if key_affix_origin in self.mappingDict and 'tipo' in self.mappingDict[key_affix_origin] and self.mappingDict[key_affix_origin]['tipo'] == 'prefixo':
                  featDict["fme_feature_type"] = featDict["fme_feature_type"][len(self.mappingDict[key_affix_origin][featDict["$GEOM_TYPE"]]):]
                  featDict["fme_feature_type_sem_afixo"] = featDict["fme_feature_type_original"][len(self.mappingDict[key_affix_origin][featDict["$GEOM_TYPE"]]):]

              should_map = False
              for classmap in self.mappingDict['mapeamento_classes']:
                  if "sentido" not in classmap or ("sentido" in classmap and classmap["sentido"] == self.mappingType):
                      if key_class_affix_origin in classmap and classmap[key_class_affix_origin] and key_class_schema_origin in classmap and classmap[key_class_schema_origin]:
                          class_name = featDict["fme_feature_type_original"]
                      elif key_class_affix_origin in classmap and classmap[key_class_affix_origin]:
                          class_name = featDict["fme_feature_type_sem_schema"]
                      elif key_class_schema_origin in classmap and classmap[key_class_schema_origin]:
                          class_name = featDict["fme_feature_type_sem_afixo"]
                      else:
                           class_name = featDict["fme_feature_type"]

                      if classmap[key_class_origin] == class_name:
                          if key_filter in classmap:
                              if not self.evaluateFilter(featDict, classmap[key_filter]):
                                  continue
                          should_map = True
              if not should_map:
                  featDict["CLASS_NOT_FOUND"] = True
                  return featDict

              mappedFeat = copy.deepcopy(featDict)

              if key_default in self.mappingDict:
                  for default in self.mappingDict[key_default]:
                      mappedFeat[default["nome_atributo"]] = default["valor"]

              if 'mapeamento_atributos' in self.mappingDict:
                  for attmap in self.mappingDict['mapeamento_atributos']:
                      if attmap[key_attr_origin] in mappedFeat:
                          mappedFeat[attmap[key_attr_destiny]] = featDict[attmap[key_attr_origin]]
                          if "traducao" in attmap:
                              for valuemap in attmap["traducao"]:
                                  if u"{0}".format(valuemap[key_value_origin]) == u"{0}".format(featDict[attmap[key_attr_origin]]) and ("sentido" not in valuemap or ("sentido" in valuemap and valuemap["sentido"] == self.mappingType)):
                                      mappedFeat[attmap[key_attr_destiny]] = valuemap[key_value_destiny]

              if "mapeamento_multiplo" in self.mappingDict:
                  for attmap in self.mappingDict['mapeamento_multiplo']:
                      if "sentido" not in attmap or ("sentido" in attmap and attmap["sentido"] == self.mappingType):
                          if all([self.evaluateExpression(featDict, condition) for condition in attmap[key_group_origin]]):
                              for valuemap in attmap[key_group_destiny]:
                                  if "concatenar" in valuemap and valuemap["concatenar"] and valuemap["nome_atributo"] in mappedFeat and mappedFeat[valuemap["nome_atributo"]]:
                                      mappedFeat[valuemap["nome_atributo"]] = mappedFeat[valuemap["nome_atributo"]] + ' | ' + valuemap["valor"]
                                  else:
                                      mappedFeat[valuemap["nome_atributo"]] = valuemap["valor"]

              if 'mapeamento_classes' in self.mappingDict:
                  for classmap in self.mappingDict['mapeamento_classes']:
                      if "sentido" not in classmap or ("sentido" in classmap and classmap["sentido"] == self.mappingType):
                          if key_class_affix_origin in classmap and classmap[key_class_affix_origin] and key_class_schema_origin in classmap and classmap[key_class_schema_origin]:
                              class_name = featDict["fme_feature_type_original"]
                          elif key_class_affix_origin in classmap and classmap[key_class_affix_origin]:
                              class_name = featDict["fme_feature_type_sem_schema"]
                          elif key_class_schema_origin in classmap and classmap[key_class_schema_origin]:
                              class_name = featDict["fme_feature_type_sem_afixo"]
                          else:
                              class_name = featDict["fme_feature_type"]

                          if classmap[key_class_origin] == class_name:
                              if key_filter in classmap:
                                  if not self.evaluateFilter(featDict, classmap[key_filter]):
                                      continue

                              mappedFeat["fme_feature_type"] = classmap[key_class_destiny]

                              if key_class_affix_destiny in classmap and classmap[key_class_affix_destiny]:
                                  pass
                              elif key_affix_destiny in self.mappingDict and 'tipo' in self.mappingDict[key_affix_destiny]:
                                  if self.mappingDict[key_affix_destiny]['tipo'] == 'sufixo':
                                      mappedFeat["fme_feature_type"] = mappedFeat["fme_feature_type"] + self.mappingDict[key_affix_destiny][featDict["$GEOM_TYPE"]]

                                  if self.mappingDict[key_affix_destiny]['tipo'] == 'prefixo':
                                      mappedFeat["fme_feature_type"] = self.mappingDict[key_affix_destiny][featDict["$GEOM_TYPE"]] + mappedFeat["fme_feature_type"]

                              if key_class_schema_destiny in classmap and classmap[key_class_schema_destiny]:
                                  pass
                              elif key_schema_destiny in self.mappingDict and self.mappingDict[key_schema_destiny]:
                                  mappedFeat["fme_feature_type"] = self.mappingDict[key_schema_destiny] + '.' + mappedFeat["fme_feature_type"]


                              if key_default in classmap:
                                  for default in classmap[key_default]:
                                      mappedFeat[default["nome_atributo"]] = default["valor"]

                              if "mapeamento_atributos" in classmap:
                                  for attmap in classmap['mapeamento_atributos']:
                                      if attmap[key_attr_origin] in featDict:
                                          if attmap[key_attr_destiny] not in mappedFeat:
                                              mappedFeat[attmap[key_attr_destiny]] = featDict[attmap[key_attr_origin]]
                                          if "traducao" in attmap:
                                              for valuemap in attmap["traducao"]:
                                                  if u"{0}".format(valuemap[key_value_origin]) == u"{0}".format(featDict[attmap[key_attr_origin]]) and ("sentido" not in valuemap or ("sentido" in valuemap and valuemap["sentido"] == self.mappingType)):
                                                      mappedFeat[attmap[key_attr_destiny]] = valuemap[key_value_destiny]

                              if "mapeamento_multiplo" in classmap:
                                  for attmap in classmap['mapeamento_multiplo']:
                                      if "sentido" not in attmap or ("sentido" in attmap and attmap["sentido"] == self.mappingType):
                                          if all([self.evaluateExpression(featDict, condition) for condition in attmap[key_group_origin]]):
                                              for valuemap in attmap[key_group_destiny]:
                                                  if "concatenar" in valuemap and valuemap["concatenar"] and valuemap["nome_atributo"] in mappedFeat and mappedFeat[valuemap["nome_atributo"]]:
                                                      mappedFeat[valuemap["nome_atributo"]] = mappedFeat[valuemap["nome_atributo"]] + ' | ' + valuemap["valor"]
                                                  else:
                                                      mappedFeat[valuemap["nome_atributo"]] = valuemap["valor"]

                              if key_agregar in classmap:
                                  mappedFeat["AGGREGATE_GEOM"] = classmap[key_agregar]
                              elif key_agregar in self.mappingDict:
                                  mappedFeat["AGGREGATE_GEOM"] = self.mappingDict[key_agregar]

                              break

              return mappedFeat

          def mapDictToFeature(self, feat, featDict):
              for attr, value in featDict.items():
                  if value == 'True':
                      feat.setAttribute(attr, 1)
                  elif value == 'False':
                      feat.setAttribute(attr, 0)
                  elif value or value == 0:
                      feat.setAttribute(attr, u'{0}'.format(value))
                  else:
                      feat.setAttributeNullWithType(attr,0)
              if "AGGREGATE_GEOM" in featDict and featDict["AGGREGATE_GEOM"]:
                  feat.buildAggregateFeat([feat])
              return feat

          def input(self,feature):
              if feature.performFunction('@GeometryType()') == 'fme_aggregate':
                  features = feature.splitAggregate(True)
              else:
                  features = [feature]
              for simple_feature in features:
                  feat = self.buildFeatureDict(simple_feature)
                  if "INVALID_GEOM" in feat and feat["INVALID_GEOM"]:
                      simple_feature.setAttribute("INVALID_GEOM", u'True')
                      self.pyoutput(simple_feature)
                      continue

                  outputFeatDict = self.convertFeature(feat)
                  if "CLASS_NOT_FOUND" in outputFeatDict and not outputFeatDict["CLASS_NOT_FOUND"]:
                      simple_feature.setAttribute("CLASS_NOT_FOUND", u'True')
                      self.pyoutput(simple_feature)
                  else:
                      outputFeature = self.mapDictToFeature(simple_feature, outputFeatDict)
                      self.pyoutput(outputFeature)

          def close(self):
              pass
    PYTHONSYMBOL = FeatureProcessor
    -> Tester_2
Note: Teste de invalid geom
Tester_2
    BOOL_OP = OR
    TEST_CLAUSE = TEST @Value(INVALID_GEOM) = True
    TEST_MODE = TEST
    PASSED -> Tester_2_Passed
    FAILED -> Tester_4
Tester_2_Passed: Inspector
Note: Teste de mapeamento
Tester_4
    BOOL_OP = OR
    TEST_CLAUSE = TEST @Value(CLASS_NOT_FOUND) = True
    TEST_MODE = TEST
    PASSED -> DuplicateFilter
    FAILED -> UniqueIdentifierGenerator
DuplicateFilter
    INPUT_ORDERED_CHOICE = No
    KEYATTR = fme_feature_type
    UNIQUE -> CLASS_NOT_FOUND
CLASS_NOT_FOUND: Inspector
UniqueIdentifierGenerator
    UUID_ATTR = id
    UUID_FORMAT = UUID_ONLY
    -> Table1 (writer POSTGIS_6)
Table1 (writer POSTGIS_6)
Tester_5_Failed: Inspector
Note: multiescala
aux_insumo_externo_100k_a (reader POSTGIS_7)
    attributes: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
