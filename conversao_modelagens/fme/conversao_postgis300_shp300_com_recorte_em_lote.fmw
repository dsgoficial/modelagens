FME workspace conversao_postgis300_shp300_com_recorte_em_lote.fmw

Parameters:
- ESPG = 4674
- SourceDataset_POSTGIS = sisfron_2024_50k_4674_edgv300   # Database
- postgis_sql_where_clause =   # "" WHERE Clause
- HOST_POSTGIS = 10.25.163.12   # Host PG
- PORT_POSTGIS = 5432   # Port PG
- USER_NAME_POSTGIS = postgres   # Username PG
- PASSWORD_POSTGIS =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   # Password PG
- JsonMapeamento = C:\Diniz\modelagens\conversao_modelagens\arquivos_mapeamento\conversao_pg-edgv-300_shp-edgv-300.json   # Arquivo de mapeamento
- SourceDataset_ESRISHAPE =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   # SHPs de referência
- DestDataset_SHAPEFILE = C:\Users\diniz\Documents\export   # Destination Esri Shapefile Folder
- WORKSPACE_FILE = $(FME_MF_DIR)conversao_postgis300_shp300_com_recorte.fmw   # FME Workspace

Readers:
- POSTGIS_1: POSTGIS from $(SourceDataset_POSTGIS)

aux_moldura_a (reader POSTGIS_1)
    attributes: id serial, escala varchar(255), inom varchar(255), mi varchar(255), nome varchar(255)
    -> GeometryExtractor
GeometryExtractor
    ATTR = _geometry
    KIND_LONG = OGC Well Known Text
    OGCVERSION = 1.2
    OGC_WKT_PRECISION_DISPLAY = 64-bit
    REMOVE_GEOMETRY = No
    -> AttributeCreator
AttributeCreator
    ATTR_TABLE = SET_TO ewkt = SRID=$(ESPG);@Value(_geometry)
    -> WorkspaceRunner
WorkspaceRunner
    BLOCKING = Yes
    WORKSPACE_FILE = $(WORKSPACE_FILE)
    WORKSPACE_PARAMETERS = SourceDataset_POSTGIS,$(SourceDataset_POSTGIS),HOST_POSTGIS,$(HOST_POSTGIS),PORT_POSTGIS,$(PORT_POSTGIS),USER_NAME_POSTGIS,$(USER_NAME_POSTGIS),PASSWORD_POSTGIS,$(PASSWORD_POSTGIS),direcao,A=>B,JsonMapeamento,$(JsonMapeamento),SourceDataset_ESRISHAPE,$(SourceDataset_ESRISHAPE),dbarea_where_clause,@Value(ewkt),DestDataset_SHAPEFILE,$(DestDataset_SHAPEFILE)\@Value(mi)
    SUCCEEDED -> WorkspaceRunner_Succeeded
    FAILED -> WorkspaceRunner_Failed
    SUMMARY -> WorkspaceRunner_Summary
WorkspaceRunner_Succeeded: Inspector
WorkspaceRunner_Failed: Inspector
WorkspaceRunner_Summary: Inspector
