FME workspace conversao_postgis300orto25_postgis300topo14.fmw

Parameters:
- JsonMapeamento = C:\Diniz\modelagens\conversao_modelagens\arquivos_mapeamento\conversao_pg-edgv-300topo14_pg-edgv-300orto25.json   # Arquivo de mapeamento
- SourceDataset_POSTGIS = orto25   # Database origem (Topo)
- HOST_POSTGIS = localhost   # Host Origem
- PORT_POSTGIS = 5433   # Porta Origem
- USER_NAME_POSTGIS = postgres   # Username Origem
- PASSWORD_POSTGIS =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   # Password Origem
- DestDataset_POSTGIS = topo14_lixo   # Database destino
- HOST_POSTGIS_2 = localhost   # Host Destino
- PORT_POSTGIS_2 = 5433   # Porta Destino
- USER_NAME_POSTGIS_2 = postgres   # Username Destino
- PASSWORD_POSTGIS_2 =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   # Password Destino
- FEATURE_TYPES = edgv.aux_insumo_externo_a edgv.aux_insumo_externo_l edgv.aux_insumo_externo_p edgv.aux_moldura_a edgv.aux_moldura_area_continua_a edgv.aux_revisao_a edgv.aux_revisao_l edgv.aux_revisao_p edgv.aux_validacao_a edgv.aux_validacao_l edgv.aux_validacao_p edgv.centroide_area_sem_dados_p edgv.centroide_elemento_hidrografico_p edgv.centroide_ilha_p edgv.centroide_limite_especial_p edgv.centroide_massa_dagua_p edgv.cobter_massa_dagua_a edgv.constr_extracao_mineral_a edgv.constr_extracao_mineral_p edgv.delimitador_area_sem_dados_l edgv.delimitador_elemento_hidrografico_l edgv.delimitador_limite_especial_l edgv.delimitador_massa_dagua_l edgv.edicao_grid_edicao_l edgv.edicao_identificador_trecho_rod_p edgv.edicao_simb_area_p edgv.edicao_simb_cota_mestra_l edgv.edicao_simb_torre_energia_p edgv.edicao_texto_generico_l edgv.edicao_texto_generico_p edgv.elemnat_curva_nivel_l edgv.elemnat_elemento_hidrografico_a edgv.elemnat_elemento_hidrografico_l edgv.elemnat_elemento_hidrografico_p edgv.elemnat_ilha_a edgv.elemnat_ilha_p edgv.elemnat_ponto_cotado_p edgv.elemnat_sumidouro_vertedouro_p edgv.elemnat_terreno_sujeito_inundacao_a edgv.elemnat_toponimo_fisiografico_natural_l edgv.elemnat_toponimo_fisiografico_natural_p edgv.elemnat_trecho_drenagem_l edgv.infra_barragem_a edgv.infra_barragem_l edgv.infra_elemento_energia_a edgv.infra_elemento_energia_l edgv.infra_elemento_energia_p edgv.infra_elemento_infraestrutura_a edgv.infra_elemento_infraestrutura_l edgv.infra_elemento_infraestrutura_p edgv.infra_ferrovia_l edgv.infra_obstaculo_vertical_p edgv.infra_pista_pouso_a edgv.infra_pista_pouso_l edgv.infra_pista_pouso_p edgv.infra_via_deslocamento_l edgv.llp_area_sem_dados_a edgv.llp_limite_legal_l edgv.llp_localidade_p edgv.llp_pais_a edgv.llp_unidade_federacao_a edgv.aux_reambulacao_a edgv.aux_reambulacao_l edgv.aux_reambulacao_p edgv.centroide_area_edificada_p edgv.centroide_vegetacao_p edgv.cobter_area_edificada_a edgv.cobter_vegetacao_a edgv.constr_area_uso_especifico_a edgv.constr_deposito_a edgv.constr_deposito_p edgv.constr_edificacao_a edgv.constr_edificacao_p edgv.constr_ocupacao_solo_a edgv.constr_ocupacao_solo_l edgv.constr_ocupacao_solo_p edgv.delimitador_area_edificada_l edgv.delimitador_vegetacao_l edgv.edicao_borda_elemento_hidrografico_l edgv.edicao_limite_especial_l edgv.edicao_ponto_mudanca_p edgv.edicao_simb_direcao_corrente_p edgv.edicao_simb_vegetacao_p edgv.elemnat_elemento_fisiografico_a edgv.elemnat_elemento_fisiografico_l edgv.elemnat_elemento_fisiografico_p edgv.infra_alteracao_fisiografica_antropica_l edgv.infra_elemento_viario_l edgv.infra_mobilidade_urbana_l edgv.infra_travessia_hidroviaria_l edgv.infra_travessia_hidroviaria_p edgv.infra_trecho_duto_l edgv.infra_trecho_hidroviario_l edgv.infra_vala_l edgv.llp_limite_especial_a edgv.llp_ponto_controle_p
- FEATURE_TYPES_2 = edgv.aux_insumo_externo_a edgv.aux_insumo_externo_l edgv.aux_insumo_externo_p edgv.aux_moldura_a edgv.aux_moldura_area_continua_a edgv.aux_revisao_a edgv.aux_revisao_l edgv.aux_revisao_p edgv.aux_validacao_a edgv.aux_validacao_l edgv.aux_validacao_p edgv.centroide_area_sem_dados_p edgv.centroide_elemento_hidrografico_p edgv.centroide_ilha_p edgv.centroide_limite_especial_p edgv.centroide_massa_dagua_p edgv.cobter_massa_dagua_a edgv.constr_extracao_mineral_a edgv.constr_extracao_mineral_p edgv.delimitador_area_sem_dados_l edgv.delimitador_elemento_hidrografico_l edgv.delimitador_limite_especial_l edgv.delimitador_massa_dagua_l edgv.edicao_grid_edicao_l edgv.edicao_identificador_trecho_rod_p edgv.edicao_simb_area_p edgv.edicao_simb_cota_mestra_l edgv.edicao_simb_torre_energia_p edgv.edicao_texto_generico_l edgv.edicao_texto_generico_p edgv.elemnat_curva_nivel_l edgv.elemnat_elemento_hidrografico_a edgv.elemnat_elemento_hidrografico_l edgv.elemnat_elemento_hidrografico_p edgv.elemnat_ilha_a edgv.elemnat_ilha_p edgv.elemnat_ponto_cotado_p edgv.elemnat_sumidouro_vertedouro_p edgv.elemnat_terreno_sujeito_inundacao_a edgv.elemnat_toponimo_fisiografico_natural_l edgv.elemnat_toponimo_fisiografico_natural_p edgv.elemnat_trecho_drenagem_l edgv.infra_barragem_a edgv.infra_barragem_l edgv.infra_elemento_energia_a edgv.infra_elemento_energia_l edgv.infra_elemento_energia_p edgv.infra_elemento_infraestrutura_a edgv.infra_elemento_infraestrutura_l edgv.infra_elemento_infraestrutura_p edgv.infra_ferrovia_l edgv.infra_obstaculo_vertical_p edgv.infra_pista_pouso_a edgv.infra_pista_pouso_l edgv.infra_pista_pouso_p edgv.infra_via_deslocamento_l edgv.llp_area_sem_dados_a edgv.llp_limite_legal_l edgv.llp_localidade_p edgv.llp_pais_a edgv.llp_unidade_federacao_a edgv.edicao_area_pub_militar_l edgv.edicao_articulacao_imagem_a edgv.edicao_terra_indigena_l edgv.edicao_unidade_conservacao_l edgv.llp_aglomerado_rural_p edgv.llp_area_pub_militar_a edgv.llp_nome_local_p edgv.llp_terra_indigena_a edgv.llp_unidade_conservacao_a
- direcao = B=>A   # Direção do mapeamento

Readers:
- POSTGIS_1: POSTGIS from $(DestDataset_POSTGIS)
- POSTGIS_2: POSTGIS from $(SourceDataset_POSTGIS)

Writers:
- POSTGIS_3: POSTGIS to $(DestDataset_POSTGIS)

aer_pista_ponto_pouso_a (reader POSTGIS_1)
    attributes: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
aquisicao_centroide_area_construida_p (reader POSTGIS_2)
    attributes: id serial, nome varchar(255), densamente_edificada int2, assentamento_precario int2, observacao varchar(255), data_modificacao timestamptz, controle_uuid varchar(255), usuario_criacao varchar(255), usuario_atualizacao varchar(255), insumo varchar(255), data_insumo timestamptz, administracao int2, altitude_geometrica varchar(255), altitude_ortometrica varchar(255), canteiro_divisorio int2, cod_ponto varchar(255), concessionaria varchar(255), corrigido int2, cota int4, cota_comprovada int2, depressao int2, descricao varchar(255), em_arruamento int2, em_via_deslocamento int2, finalidade int2, fonte varchar(255), forma_extracao int2, geometria_aproximada int2, indice int2, inom varchar(255),
      jurisdicao int2, justificativa varchar(255), latitude varchar(255), longitude varchar(255), material_construcao int2, mi varchar(255), modal_uso int2, nr_faixas varchar(255), nr_linhas int2, nr_pistas varchar(255), orgao_responsavel varchar(255), populacao int4, posicao_pista int2, posicao_relativa int2, referencial_altim int2, referencial_grav int2, regime int2, revestimento int2, sigla varchar(255), sistema_geodesico int2, situacao_em_poligono int2, situacao_fisica int2, situacao_marco int2, subfase_id int4, sujeito_inundacao int2, tipo int2, tipo_exposicao int2, tipo_ref int2, trafego int2, uso_pista int2
    -> PythonCaller_EDGV3
Note: mapeamento
PythonCaller_EDGV3
    NEW_ATTRIBUTES = CLASS_NOT_FOUND INVALID_GEOM
    PYTHONSOURCE:
      import fme
      import fmeobjects
      import copy
      import sys
      import os
      import json

      class FeatureProcessor(object):
          def __init__(self):
              self.mappingDict = self.buildFileDict(FME_MacroValues['JsonMapeamento'])
              self.mappingType = FME_MacroValues['direcao']

          def buildFileDict(self, mappingPath):
              with open(mappingPath, 'r', encoding='utf-8') as file:
                  mapDict = json.loads(file.read())
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          if feature.getAttribute(attr) == 'f':
                              featDict[attr] = 'False'
                          elif feature.getAttribute(attr) == 't':
                              featDict[attr] = 'True'
                          else:
                              featDict[attr] = feature.getAttribute(attr)
                      else:
                          featDict[attr] = None
              if feature.performFunction('@GeometryType()') == 'fme_polygon' or feature.performFunction('@GeometryType()') == 'fme_donut':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              else:
                   featDict["INVALID_GEOM"] = True
              return featDict

          def evaluateExpression(self, featDict, expression):
              if not expression["nome_atributo"] in featDict:
                  return False
              if expression["valor"] is None or expression["valor"] == "":
                  return featDict[expression["nome_atributo"]] is None or featDict[expression["nome_atributo"]] == ""
              else:
                  return u"{0}".format(featDict[expression["nome_atributo"]]) == u"{0}".format(expression["valor"])

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "A=>B":
                  key_attr_origin = "attr_A"
                  key_attr_destiny = "attr_B"
                  key_value_origin = "valor_A"
                  key_value_destiny = "valor_B"
                  key_default = "atributos_default_B"
                  key_filter = "filtro_A"
                  key_class_origin = "classe_A"
                  key_class_destiny = "classe_B"
                  key_group_origin = "tupla_A"
                  key_group_destiny = "tupla_B"
                  key_affix_origin = "afixo_geom_A"
                  key_affix_destiny = "afixo_geom_B"
                  key_schema_origin = "schema_A"
                  key_schema_destiny = "schema_B"
                  key_class_affix_origin = "com_afixo_geom_A"
                  key_class_affix_destiny = "com_afixo_geom_B"
                  key_class_schema_origin = "com_schema_A"
                  key_class_schema_destiny = "com_schema_B"
                  key_agregar = "agregar_geom_A"
              else:
                  key_attr_origin = "attr_B"
                  key_attr_destiny = "attr_A"
                  key_value_origin = "valor_B"
                  key_value_destiny = "valor_A"
                  key_default = "atributos_default_A"
                  key_filter = "filtro_B"
                  key_class_origin = "classe_B"
                  key_class_destiny = "classe_A"
                  key_group_origin = "tupla_B"
                  key_group_destiny = "tupla_A"
                  key_affix_origin = "afixo_geom_B"
                  key_affix_destiny = "afixo_geom_A"
                  key_schema_origin = "schema_B"
                  key_schema_destiny = "schema_A"
                  key_class_affix_origin = "com_afixo_geom_B"
                  key_class_affix_destiny = "com_afixo_geom_A"
                  key_class_schema_origin = "com_schema_B"
                  key_class_schema_destiny = "com_schema_A"
                  key_agregar = "agregar_geom_B"

              featDict["fme_feature_type_original"] = featDict["fme_feature_type"]

              if key_schema_origin in self.mappingDict and self.mappingDict[key_schema_origin]:
                  featDict["fme_feature_type"] = featDict["fme_feature_type"][len(self.mappingDict[key_schema_origin])+1:]

              featDict["fme_feature_type_sem_schema"] = featDict["fme_feature_type"]

              if key_affix_origin in self.mappingDict and 'tipo' in self.mappingDict[key_affix_origin] and self.mappingDict[key_affix_origin]['tipo'] == 'sufixo':
                  featDict["fme_feature_type"] = featDict["fme_feature_type"][:-len(self.mappingDict[key_affix_origin][featDict["$GEOM_TYPE"]])]
                  featDict["fme_feature_type_sem_afixo"] = featDict["fme_feature_type_original"][:-len(self.mappingDict[key_affix_origin][featDict["$GEOM_TYPE"]])]

              if key_affix_origin in self.mappingDict and 'tipo' in self.mappingDict[key_affix_origin] and self.mappingDict[key_affix_origin]['tipo'] == 'prefixo':
                  featDict["fme_feature_type"] = featDict["fme_feature_type"][len(self.mappingDict[key_affix_origin][featDict["$GEOM_TYPE"]]):]
                  featDict["fme_feature_type_sem_afixo"] = featDict["fme_feature_type_original"][len(self.mappingDict[key_affix_origin][featDict["$GEOM_TYPE"]]):]

              should_map = False
              for classmap in self.mappingDict['mapeamento_classes']:
                  if "sentido" not in classmap or ("sentido" in classmap and classmap["sentido"] == self.mappingType):
                      if key_class_affix_origin in classmap and classmap[key_class_affix_origin] and key_class_schema_origin in classmap and classmap[key_class_schema_origin]:
                          class_name = featDict["fme_feature_type_original"]
                      elif key_class_affix_origin in classmap and classmap[key_class_affix_origin]:
                          class_name = featDict["fme_feature_type_sem_schema"]
                      elif key_class_schema_origin in classmap and classmap[key_class_schema_origin]:
                          class_name = featDict["fme_feature_type_sem_afixo"]
                      else:
                           class_name = featDict["fme_feature_type"]

                      if classmap[key_class_origin] == class_name:
                          if key_filter in classmap:
                              if not self.evaluateFilter(featDict, classmap[key_filter]):
                                  continue
                          should_map = True
              if not should_map:
                  featDict["CLASS_NOT_FOUND"] = True
                  return featDict

              mappedFeat = copy.deepcopy(featDict)

              if key_default in self.mappingDict:
                  for default in self.mappingDict[key_default]:
                      mappedFeat[default["nome_atributo"]] = default["valor"]

              if 'mapeamento_atributos' in self.mappingDict:
                  for attmap in self.mappingDict['mapeamento_atributos']:
                      if attmap[key_attr_origin] in mappedFeat:
                          mappedFeat[attmap[key_attr_destiny]] = featDict[attmap[key_attr_origin]]
                          if "traducao" in attmap:
                              for valuemap in attmap["traducao"]:
                                  if u"{0}".format(valuemap[key_value_origin]) == u"{0}".format(featDict[attmap[key_attr_origin]]) and ("sentido" not in valuemap or ("sentido" in valuemap and valuemap["sentido"] == self.mappingType)):
                                      mappedFeat[attmap[key_attr_destiny]] = valuemap[key_value_destiny]

              if "mapeamento_multiplo" in self.mappingDict:
                  for attmap in self.mappingDict['mapeamento_multiplo']:
                      if "sentido" not in attmap or ("sentido" in attmap and attmap["sentido"] == self.mappingType):
                          if all([self.evaluateExpression(featDict, condition) for condition in attmap[key_group_origin]]):
                              for valuemap in attmap[key_group_destiny]:
                                  if "concatenar" in valuemap and valuemap["concatenar"] and valuemap["nome_atributo"] in mappedFeat and mappedFeat[valuemap["nome_atributo"]]:
                                      mappedFeat[valuemap["nome_atributo"]] = mappedFeat[valuemap["nome_atributo"]] + ' | ' + valuemap["valor"]
                                  else:
                                      mappedFeat[valuemap["nome_atributo"]] = valuemap["valor"]

              if 'mapeamento_classes' in self.mappingDict:
                  for classmap in self.mappingDict['mapeamento_classes']:
                      if "sentido" not in classmap or ("sentido" in classmap and classmap["sentido"] == self.mappingType):
                          if key_class_affix_origin in classmap and classmap[key_class_affix_origin] and key_class_schema_origin in classmap and classmap[key_class_schema_origin]:
                              class_name = featDict["fme_feature_type_original"]
                          elif key_class_affix_origin in classmap and classmap[key_class_affix_origin]:
                              class_name = featDict["fme_feature_type_sem_schema"]
                          elif key_class_schema_origin in classmap and classmap[key_class_schema_origin]:
                              class_name = featDict["fme_feature_type_sem_afixo"]
                          else:
                              class_name = featDict["fme_feature_type"]

                          if classmap[key_class_origin] == class_name:
                              if key_filter in classmap:
                                  if not self.evaluateFilter(featDict, classmap[key_filter]):
                                      continue

                              mappedFeat["fme_feature_type"] = classmap[key_class_destiny]

                              if key_class_affix_destiny in classmap and classmap[key_class_affix_destiny]:
                                  pass
                              elif key_affix_destiny in self.mappingDict and 'tipo' in self.mappingDict[key_affix_destiny]:
                                  if self.mappingDict[key_affix_destiny]['tipo'] == 'sufixo':
                                      mappedFeat["fme_feature_type"] = mappedFeat["fme_feature_type"] + self.mappingDict[key_affix_destiny][featDict["$GEOM_TYPE"]]

                                  if self.mappingDict[key_affix_destiny]['tipo'] == 'prefixo':
                                      mappedFeat["fme_feature_type"] = self.mappingDict[key_affix_destiny][featDict["$GEOM_TYPE"]] + mappedFeat["fme_feature_type"]

                              if key_class_schema_destiny in classmap and classmap[key_class_schema_destiny]:
                                  pass
                              elif key_schema_destiny in self.mappingDict and self.mappingDict[key_schema_destiny]:
                                  mappedFeat["fme_feature_type"] = self.mappingDict[key_schema_destiny] + '.' + mappedFeat["fme_feature_type"]


                              if key_default in classmap:
                                  for default in classmap[key_default]:
                                      mappedFeat[default["nome_atributo"]] = default["valor"]

                              if "mapeamento_atributos" in classmap:
                                  for attmap in classmap['mapeamento_atributos']:
                                      if attmap[key_attr_origin] in featDict:
                                          if attmap[key_attr_destiny] not in mappedFeat:
                                              mappedFeat[attmap[key_attr_destiny]] = featDict[attmap[key_attr_origin]]
                                          if "traducao" in attmap:
                                              for valuemap in attmap["traducao"]:
                                                  if u"{0}".format(valuemap[key_value_origin]) == u"{0}".format(featDict[attmap[key_attr_origin]]) and ("sentido" not in valuemap or ("sentido" in valuemap and valuemap["sentido"] == self.mappingType)):
                                                      mappedFeat[attmap[key_attr_destiny]] = valuemap[key_value_destiny]

                              if "mapeamento_multiplo" in classmap:
                                  for attmap in classmap['mapeamento_multiplo']:
                                      if "sentido" not in attmap or ("sentido" in attmap and attmap["sentido"] == self.mappingType):
                                          if all([self.evaluateExpression(featDict, condition) for condition in attmap[key_group_origin]]):
                                              for valuemap in attmap[key_group_destiny]:
                                                  if "concatenar" in valuemap and valuemap["concatenar"] and valuemap["nome_atributo"] in mappedFeat and mappedFeat[valuemap["nome_atributo"]]:
                                                      mappedFeat[valuemap["nome_atributo"]] = mappedFeat[valuemap["nome_atributo"]] + ' | ' + valuemap["valor"]
                                                  else:
                                                      mappedFeat[valuemap["nome_atributo"]] = valuemap["valor"]

                              if key_agregar in classmap:
                                  mappedFeat["AGGREGATE_GEOM"] = classmap[key_agregar]
                              elif key_agregar in self.mappingDict:
                                  mappedFeat["AGGREGATE_GEOM"] = self.mappingDict[key_agregar]

                              break

              return mappedFeat

          def mapDictToFeature(self, feat, featDict):
              for attr, value in featDict.items():
                  if value == 'True':
                      feat.setAttribute(attr, 1)
                  elif value == 'False':
                      feat.setAttribute(attr, 0)
                  elif value or value == 0:
                      feat.setAttribute(attr, u'{0}'.format(value))
                  else:
                      feat.setAttributeNullWithType(attr,0)
              if "AGGREGATE_GEOM" in featDict and featDict["AGGREGATE_GEOM"]:
                  feat.buildAggregateFeat([feat])
              return feat

          def input(self,feature):
              if feature.performFunction('@GeometryType()') == 'fme_aggregate':
                  features = feature.splitAggregate(True)
              else:
                  features = [feature]
              for simple_feature in features:
                  feat = self.buildFeatureDict(simple_feature)
                  if "INVALID_GEOM" in feat and feat["INVALID_GEOM"]:
                      simple_feature.setAttribute("INVALID_GEOM", u'True')
                      self.pyoutput(simple_feature)
                      continue

                  outputFeatDict = self.convertFeature(feat)
                  if "CLASS_NOT_FOUND" in outputFeatDict and not outputFeatDict["CLASS_NOT_FOUND"]:
                      simple_feature.setAttribute("CLASS_NOT_FOUND", u'True')
                      self.pyoutput(simple_feature)
                  else:
                      outputFeature = self.mapDictToFeature(simple_feature, outputFeatDict)
                      self.pyoutput(outputFeature)

          def close(self):
              pass
    PYTHONSYMBOL = FeatureProcessor
    -> Tester_2
Note: Teste de invalid geom
Tester_2
    BOOL_OP = OR
    TEST_CLAUSE = TEST @Value(INVALID_GEOM) = True
    TEST_MODE = TEST
    PASSED -> Tester_2_Passed
    FAILED -> Tester_4
Tester_2_Passed: Inspector
Note: Teste de mapeamento
Tester_4
    BOOL_OP = OR
    TEST_CLAUSE = TEST @Value(CLASS_NOT_FOUND) = True
    TEST_MODE = TEST
    PASSED -> DuplicateFilter
    FAILED -> Reprojector
DuplicateFilter
    INPUT_ORDERED_CHOICE = No
    KEYATTR = fme_feature_type
    UNIQUE -> CLASS_NOT_FOUND
CLASS_NOT_FOUND: Inspector
Reprojector
    DEST = EPSG:4674
    INTERPOLATION_TYPE_NAME = Nearest Neighbor
    RASTER_CELL_SIZE = Preserve Cells
    RASTER_TOLERANCE = 0.0
    REPROJECTED -> Table1 (writer POSTGIS_3)
Table1 (writer POSTGIS_3)
