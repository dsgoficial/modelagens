FME workspace combina_multiescala.fmw

Parameters:
- SourceDataset_POSTGIS = asc_multiescala_4674_edgvtopo14multi   # Database
- FEATURE_TYPES = edgv.aux_moldura_250k_a edgv.aux_moldura_area_continua_250k_a edgv.aux_observacao_250k_a edgv.aux_observacao_250k_l edgv.aux_observacao_250k_p edgv.aux_reambulacao_250k_a edgv.aux_reambulacao_250k_l edgv.aux_reambulacao_250k_p edgv.aux_revisao_250k_a edgv.aux_revisao_250k_l edgv.aux_revisao_250k_p edgv.centroide_area_edificada_250k_p edgv.centroide_area_sem_dados_250k_p edgv.centroide_elemento_hidrografico_250k_p edgv.centroide_ilha_250k_p edgv.centroide_limite_especial_250k_p edgv.centroide_massa_dagua_250k_p edgv.centroide_vegetacao_250k_p edgv.cobter_area_edificada_250k_a edgv.cobter_massa_dagua_250k_a edgv.cobter_vegetacao_250k_a edgv.constr_area_uso_especifico_250k_a edgv.constr_deposito_250k_a edgv.constr_deposito_250k_p edgv.constr_edificacao_250k_a edgv.constr_edificacao_250k_p edgv.constr_extracao_mineral_250k_a edgv.constr_extracao_mineral_250k_p edgv.constr_ocupacao_solo_250k_a edgv.constr_ocupacao_solo_250k_l edgv.constr_ocupacao_solo_250k_p edgv.delimitador_area_edificada_250k_l edgv.delimitador_area_sem_dados_250k_l edgv.delimitador_elemento_hidrografico_250k_l edgv.delimitador_limite_especial_250k_l edgv.delimitador_massa_dagua_250k_l edgv.delimitador_vegetacao_250k_l edgv.edicao_borda_elemento_hidrografico_250k_l edgv.edicao_grid_edicao_250k_l edgv.edicao_grid_numerico_250k_p edgv.edicao_identificador_trecho_rod_250k_p edgv.edicao_limite_especial_250k_l edgv.edicao_ponto_mudanca_250k_p edgv.edicao_simb_area_250k_p edgv.edicao_simb_cota_mestra_250k_l edgv.edicao_simb_direcao_corrente_250k_p edgv.edicao_simb_torre_energia_250k_p edgv.edicao_simb_vegetacao_250k_p edgv.edicao_texto_generico_250k_l edgv.edicao_texto_generico_250k_p edgv.elemnat_curva_nivel_250k_l edgv.elemnat_elemento_fisiografico_250k_a edgv.elemnat_elemento_fisiografico_250k_l edgv.elemnat_elemento_fisiografico_250k_p edgv.elemnat_elemento_hidrografico_250k_a edgv.elemnat_elemento_hidrografico_250k_l edgv.elemnat_elemento_hidrografico_250k_p edgv.elemnat_ilha_250k_a edgv.elemnat_ilha_250k_p edgv.elemnat_ponto_cotado_250k_p edgv.elemnat_sumidouro_vertedouro_250k_p edgv.elemnat_terreno_sujeito_inundacao_250k_a edgv.elemnat_toponimo_fisiografico_natural_250k_l edgv.elemnat_toponimo_fisiografico_natural_250k_p edgv.elemnat_trecho_drenagem_250k_l edgv.infra_alteracao_fisiografica_antropica_250k_l edgv.infra_barragem_250k_a edgv.infra_barragem_250k_l edgv.infra_elemento_energia_250k_a edgv.infra_elemento_energia_250k_l edgv.infra_elemento_energia_250k_p edgv.infra_elemento_infraestrutura_250k_a edgv.infra_elemento_infraestrutura_250k_l edgv.infra_elemento_infraestrutura_250k_p edgv.infra_elemento_viario_250k_l edgv.infra_ferrovia_250k_l edgv.infra_mobilidade_urbana_250k_l edgv.infra_obstaculo_vertical_250k_p edgv.infra_pista_pouso_250k_a edgv.infra_pista_pouso_250k_l edgv.infra_pista_pouso_250k_p edgv.infra_travessia_hidroviaria_250k_l edgv.infra_travessia_hidroviaria_250k_p edgv.infra_trecho_duto_250k_l edgv.infra_trecho_hidroviario_250k_l edgv.infra_vala_250k_l edgv.infra_via_deslocamento_250k_l edgv.llp_area_sem_dados_250k_a edgv.llp_limite_especial_250k_a edgv.llp_limite_legal_250k_l edgv.llp_localidade_250k_p edgv.llp_pais_250k_a edgv.llp_ponto_controle_250k_p edgv.llp_unidade_federacao_250k_a
- SourceDataset_POSTGIS_5 = asc_multiescala_4674_edgvtopo14multi   # Database
- FEATURE_TYPES_2 = edgv.aux_moldura_100k_a edgv.aux_moldura_area_continua_100k_a edgv.aux_observacao_100k_a edgv.aux_observacao_100k_l edgv.aux_observacao_100k_p edgv.aux_reambulacao_100k_a edgv.aux_reambulacao_100k_l edgv.aux_reambulacao_100k_p edgv.aux_revisao_100k_a edgv.aux_revisao_100k_l edgv.aux_revisao_100k_p edgv.centroide_area_edificada_100k_p edgv.centroide_area_sem_dados_100k_p edgv.centroide_elemento_hidrografico_100k_p edgv.centroide_ilha_100k_p edgv.centroide_limite_especial_100k_p edgv.centroide_massa_dagua_100k_p edgv.centroide_vegetacao_100k_p edgv.cobter_area_edificada_100k_a edgv.cobter_massa_dagua_100k_a edgv.cobter_vegetacao_100k_a edgv.constr_area_uso_especifico_100k_a edgv.constr_deposito_100k_a edgv.constr_deposito_100k_p edgv.constr_edificacao_100k_a edgv.constr_edificacao_100k_p edgv.constr_extracao_mineral_100k_a edgv.constr_extracao_mineral_100k_p edgv.constr_ocupacao_solo_100k_a edgv.constr_ocupacao_solo_100k_l edgv.constr_ocupacao_solo_100k_p edgv.delimitador_area_edificada_100k_l edgv.delimitador_area_sem_dados_100k_l edgv.delimitador_elemento_hidrografico_100k_l edgv.delimitador_limite_especial_100k_l edgv.delimitador_massa_dagua_100k_l edgv.delimitador_vegetacao_100k_l edgv.edicao_borda_elemento_hidrografico_100k_l edgv.edicao_grid_edicao_100k_l edgv.edicao_grid_numerico_100k_p edgv.edicao_identificador_trecho_rod_100k_p edgv.edicao_limite_especial_100k_l edgv.edicao_ponto_mudanca_100k_p edgv.edicao_simb_area_100k_p edgv.edicao_simb_cota_mestra_100k_l edgv.edicao_simb_direcao_corrente_100k_p edgv.edicao_simb_torre_energia_100k_p edgv.edicao_simb_vegetacao_100k_p edgv.edicao_texto_generico_100k_l edgv.edicao_texto_generico_100k_p edgv.elemnat_curva_nivel_100k_l edgv.elemnat_elemento_fisiografico_100k_a edgv.elemnat_elemento_fisiografico_100k_l edgv.elemnat_elemento_fisiografico_100k_p edgv.elemnat_elemento_hidrografico_100k_a edgv.elemnat_elemento_hidrografico_100k_l edgv.elemnat_elemento_hidrografico_100k_p edgv.elemnat_ilha_100k_a edgv.elemnat_ilha_100k_p edgv.elemnat_ponto_cotado_100k_p edgv.elemnat_sumidouro_vertedouro_100k_p edgv.elemnat_terreno_sujeito_inundacao_100k_a edgv.elemnat_toponimo_fisiografico_natural_100k_l edgv.elemnat_toponimo_fisiografico_natural_100k_p edgv.elemnat_trecho_drenagem_100k_l edgv.infra_alteracao_fisiografica_antropica_100k_l edgv.infra_barragem_100k_a edgv.infra_barragem_100k_l edgv.infra_elemento_energia_100k_a edgv.infra_elemento_energia_100k_l edgv.infra_elemento_energia_100k_p edgv.infra_elemento_infraestrutura_100k_a edgv.infra_elemento_infraestrutura_100k_l edgv.infra_elemento_infraestrutura_100k_p edgv.infra_elemento_viario_100k_l edgv.infra_ferrovia_100k_l edgv.infra_mobilidade_urbana_100k_l edgv.infra_obstaculo_vertical_100k_p edgv.infra_pista_pouso_100k_a edgv.infra_pista_pouso_100k_l edgv.infra_pista_pouso_100k_p edgv.infra_travessia_hidroviaria_100k_l edgv.infra_travessia_hidroviaria_100k_p edgv.infra_trecho_duto_100k_l edgv.infra_trecho_hidroviario_100k_l edgv.infra_vala_100k_l edgv.infra_via_deslocamento_100k_l edgv.llp_area_sem_dados_100k_a edgv.llp_limite_especial_100k_a edgv.llp_limite_legal_100k_l edgv.llp_localidade_100k_p edgv.llp_pais_100k_a edgv.llp_ponto_controle_100k_p edgv.llp_unidade_federacao_100k_a
- SourceDataset_POSTGIS_7 = asc_multiescala_4674_edgvtopo14multi   # Database
- FEATURE_TYPES_3 = edgv.aux_moldura_50k_a edgv.aux_moldura_area_continua_50k_a edgv.aux_observacao_50k_a edgv.aux_observacao_50k_l edgv.aux_observacao_50k_p edgv.aux_reambulacao_50k_a edgv.aux_reambulacao_50k_l edgv.aux_reambulacao_50k_p edgv.aux_revisao_50k_a edgv.aux_revisao_50k_l edgv.aux_revisao_50k_p edgv.centroide_area_edificada_50k_p edgv.centroide_area_sem_dados_50k_p edgv.centroide_elemento_hidrografico_50k_p edgv.centroide_ilha_50k_p edgv.centroide_limite_especial_50k_p edgv.centroide_massa_dagua_50k_p edgv.centroide_vegetacao_50k_p edgv.cobter_area_edificada_50k_a edgv.cobter_massa_dagua_50k_a edgv.cobter_vegetacao_50k_a edgv.constr_area_uso_especifico_50k_a edgv.constr_deposito_50k_a edgv.constr_deposito_50k_p edgv.constr_edificacao_50k_a edgv.constr_edificacao_50k_p edgv.constr_extracao_mineral_50k_a edgv.constr_extracao_mineral_50k_p edgv.constr_ocupacao_solo_50k_a edgv.constr_ocupacao_solo_50k_l edgv.constr_ocupacao_solo_50k_p edgv.delimitador_area_edificada_50k_l edgv.delimitador_area_sem_dados_50k_l edgv.delimitador_elemento_hidrografico_50k_l edgv.delimitador_limite_especial_50k_l edgv.delimitador_massa_dagua_50k_l edgv.delimitador_vegetacao_50k_l edgv.edicao_borda_elemento_hidrografico_50k_l edgv.edicao_grid_edicao_50k_l edgv.edicao_grid_numerico_50k_p edgv.edicao_identificador_trecho_rod_50k_p edgv.edicao_limite_especial_50k_l edgv.edicao_ponto_mudanca_50k_p edgv.edicao_simb_area_50k_p edgv.edicao_simb_cota_mestra_50k_l edgv.edicao_simb_direcao_corrente_50k_p edgv.edicao_simb_torre_energia_50k_p edgv.edicao_simb_vegetacao_50k_p edgv.edicao_texto_generico_50k_l edgv.edicao_texto_generico_50k_p edgv.elemnat_curva_nivel_50k_l edgv.elemnat_elemento_fisiografico_50k_a edgv.elemnat_elemento_fisiografico_50k_l edgv.elemnat_elemento_fisiografico_50k_p edgv.elemnat_elemento_hidrografico_50k_a edgv.elemnat_elemento_hidrografico_50k_l edgv.elemnat_elemento_hidrografico_50k_p edgv.elemnat_ilha_50k_a edgv.elemnat_ilha_50k_p edgv.elemnat_ponto_cotado_50k_p edgv.elemnat_sumidouro_vertedouro_50k_p edgv.elemnat_terreno_sujeito_inundacao_50k_a edgv.elemnat_toponimo_fisiografico_natural_50k_l edgv.elemnat_toponimo_fisiografico_natural_50k_p edgv.elemnat_trecho_drenagem_50k_l edgv.infra_alteracao_fisiografica_antropica_50k_l edgv.infra_barragem_50k_a edgv.infra_barragem_50k_l edgv.infra_elemento_energia_50k_a edgv.infra_elemento_energia_50k_l edgv.infra_elemento_energia_50k_p edgv.infra_elemento_infraestrutura_50k_a edgv.infra_elemento_infraestrutura_50k_l edgv.infra_elemento_infraestrutura_50k_p edgv.infra_elemento_viario_50k_l edgv.infra_ferrovia_50k_l edgv.infra_mobilidade_urbana_50k_l edgv.infra_obstaculo_vertical_50k_p edgv.infra_pista_pouso_50k_a edgv.infra_pista_pouso_50k_l edgv.infra_pista_pouso_50k_p edgv.infra_travessia_hidroviaria_50k_l edgv.infra_travessia_hidroviaria_50k_p edgv.infra_trecho_duto_50k_l edgv.infra_trecho_hidroviario_50k_l edgv.infra_vala_50k_l edgv.infra_via_deslocamento_50k_l edgv.llp_area_sem_dados_50k_a edgv.llp_limite_especial_50k_a edgv.llp_limite_legal_50k_l edgv.llp_localidade_50k_p edgv.llp_pais_50k_a edgv.llp_ponto_controle_50k_p edgv.llp_unidade_federacao_50k_a
- SourceDataset_POSTGIS_6 = asc_multiescala_4674_edgvtopo14multi   # Database
- FEATURE_TYPES_4 = edgv.aux_moldura_25k_a edgv.aux_moldura_area_continua_25k_a edgv.aux_observacao_25k_a edgv.aux_observacao_25k_l edgv.aux_observacao_25k_p edgv.aux_reambulacao_25k_a edgv.aux_reambulacao_25k_l edgv.aux_reambulacao_25k_p edgv.aux_revisao_25k_a edgv.aux_revisao_25k_l edgv.aux_revisao_25k_p edgv.centroide_area_edificada_25k_p edgv.centroide_area_sem_dados_25k_p edgv.centroide_elemento_hidrografico_25k_p edgv.centroide_ilha_25k_p edgv.centroide_limite_especial_25k_p edgv.centroide_massa_dagua_25k_p edgv.centroide_vegetacao_25k_p edgv.cobter_area_edificada_25k_a edgv.cobter_massa_dagua_25k_a edgv.cobter_vegetacao_25k_a edgv.constr_area_uso_especifico_25k_a edgv.constr_deposito_25k_a edgv.constr_deposito_25k_p edgv.constr_edificacao_25k_a edgv.constr_edificacao_25k_p edgv.constr_extracao_mineral_25k_a edgv.constr_extracao_mineral_25k_p edgv.constr_ocupacao_solo_25k_a edgv.constr_ocupacao_solo_25k_l edgv.constr_ocupacao_solo_25k_p edgv.delimitador_area_edificada_25k_l edgv.delimitador_area_sem_dados_25k_l edgv.delimitador_elemento_hidrografico_25k_l edgv.delimitador_limite_especial_25k_l edgv.delimitador_massa_dagua_25k_l edgv.delimitador_vegetacao_25k_l edgv.edicao_borda_elemento_hidrografico_25k_l edgv.edicao_grid_edicao_25k_l edgv.edicao_grid_numerico_25k_p edgv.edicao_identificador_trecho_rod_25k_p edgv.edicao_limite_especial_25k_l edgv.edicao_ponto_mudanca_25k_p edgv.edicao_simb_area_25k_p edgv.edicao_simb_cota_mestra_25k_l edgv.edicao_simb_direcao_corrente_25k_p edgv.edicao_simb_torre_energia_25k_p edgv.edicao_simb_vegetacao_25k_p edgv.edicao_texto_generico_25k_l edgv.edicao_texto_generico_25k_p edgv.elemnat_curva_nivel_25k_l edgv.elemnat_elemento_fisiografico_25k_a edgv.elemnat_elemento_fisiografico_25k_l edgv.elemnat_elemento_fisiografico_25k_p edgv.elemnat_elemento_hidrografico_25k_a edgv.elemnat_elemento_hidrografico_25k_l edgv.elemnat_elemento_hidrografico_25k_p edgv.elemnat_ilha_25k_a edgv.elemnat_ilha_25k_p edgv.elemnat_ponto_cotado_25k_p edgv.elemnat_sumidouro_vertedouro_25k_p edgv.elemnat_terreno_sujeito_inundacao_25k_a edgv.elemnat_toponimo_fisiografico_natural_25k_l edgv.elemnat_toponimo_fisiografico_natural_25k_p edgv.elemnat_trecho_drenagem_25k_l edgv.infra_alteracao_fisiografica_antropica_25k_l edgv.infra_barragem_25k_a edgv.infra_barragem_25k_l edgv.infra_elemento_energia_25k_a edgv.infra_elemento_energia_25k_l edgv.infra_elemento_energia_25k_p edgv.infra_elemento_infraestrutura_25k_a edgv.infra_elemento_infraestrutura_25k_l edgv.infra_elemento_infraestrutura_25k_p edgv.infra_elemento_viario_25k_l edgv.infra_ferrovia_25k_l edgv.infra_mobilidade_urbana_25k_l edgv.infra_obstaculo_vertical_25k_p edgv.infra_pista_pouso_25k_a edgv.infra_pista_pouso_25k_l edgv.infra_pista_pouso_25k_p edgv.infra_travessia_hidroviaria_25k_l edgv.infra_travessia_hidroviaria_25k_p edgv.infra_trecho_duto_25k_l edgv.infra_trecho_hidroviario_25k_l edgv.infra_vala_25k_l edgv.infra_via_deslocamento_25k_l edgv.llp_area_sem_dados_25k_a edgv.llp_limite_especial_25k_a edgv.llp_limite_legal_25k_l edgv.llp_localidade_25k_p edgv.llp_pais_25k_a edgv.llp_ponto_controle_25k_p edgv.llp_unidade_federacao_25k_a
- DestDataset_POSTGIS = operacao_fogo_4674_edgvtopo14multi   # Database

Readers:
- POSTGIS_1: POSTGIS from $(SourceDataset_POSTGIS)
- POSTGIS_2: POSTGIS from $(SourceDataset_POSTGIS_5)
- POSTGIS_3: POSTGIS from $(SourceDataset_POSTGIS_7)
- POSTGIS_4: POSTGIS from $(SourceDataset_POSTGIS_6)

Writers:
- POSTGIS_5: POSTGIS to $(DestDataset_POSTGIS)

Note: 250k
aux_moldura_250k_a (reader POSTGIS_1)
    attributes: id uuid, nome varchar(255), mi varchar(255), inom varchar(255), observacao varchar(255), administracao_code int2, administracao_value varchar(255), altitude float4, altitude_geometrica varchar(255), altitude_ortometrica varchar(255), altura float4, ancora_horizontal_code int2, ancora_horizontal_value varchar(255), ancora_vertical_code int2, ancora_vertical_value varchar(255), assentamento_precario_code int2, assentamento_precario_value varchar(255), bitola_code int2, bitola_value varchar(255), canteiro_divisorio_code int2, canteiro_divisorio_value varchar(255), cod_ponto varchar(255), concessionaria varchar(255), config_comprimento_simb_code int2, config_comprimento_simb_value varchar(255), cor varchar(255), corrigido_code int2, corrigido_value varchar(255), cota int4, cota_comprovada_code int2,
      cota_comprovada_value varchar(255), cota_mais_alta_code int2, cota_mais_alta_value varchar(255), dentro_massa_dagua_code int2, dentro_massa_dagua_value varchar(255), depressao_code int2, depressao_value varchar(255), descricao varchar(255), desloc float4, direcao varchar(255), direcao_fixada_code int2, direcao_fixada_value varchar(255), eletrificada_code int2, eletrificada_value varchar(255), em_arruamento_code int2, em_arruamento_value varchar(255), em_galeria_bueiro_code int2, em_galeria_bueiro_value varchar(255), espacamento float4, estilo_fonte varchar(255), exibir_lado_simbologia_code int2, exibir_lado_simbologia_value varchar(255), exibir_linha_rotulo_code int2, exibir_linha_rotulo_value varchar(255), exibir_ponta_simbologia_code int2, exibir_ponta_simbologia_value varchar(255), exibir_rotulo_aproximado_code int2, exibir_rotulo_aproximado_value varchar(255), finalidade_code int2, finalidade_value varchar(255),
      forma_extracao_code int2, forma_extracao_value varchar(255), geometria_aproximada_code int2, geometria_aproximada_value varchar(255), indice_code int2, indice_value varchar(255), jurisdicao_code int2, jurisdicao_value varchar(255), justificativa varchar(255), justificativa_txt_code int2, justificativa_txt_value varchar(255), label_x float4, label_y float4, largura_simbologia float4, latitude varchar(255), longitude varchar(255), material_construcao_code int2, material_construcao_elemento_viario_code int2, material_construcao_elemento_viario_value varchar(255), material_construcao_value varchar(255), modal_uso_code int2, modal_uso_value varchar(255), nome_elemento_viario varchar(255), nr_faixas varchar(255), nr_linhas_code int2, nr_linhas_value varchar(255), nr_pistas varchar(255), numero varchar(255), ordem_simbologia int4, orgao_responsavel varchar(255),
      populacao int4, posicao_pista_code int2, posicao_pista_elemento_viario_code int2, posicao_pista_elemento_viario_value varchar(255), posicao_pista_value varchar(255), posicao_relativa_code int2, posicao_relativa_value varchar(255), posicao_rotulo_code int2, posicao_rotulo_value varchar(255), referencial_altim_code int2, referencial_altim_value varchar(255), referencial_grav_code int2, referencial_grav_value varchar(255), regime_code int2, regime_value varchar(255), revestimento_code int2, revestimento_value varchar(255), sigla varchar(255), sigla_code int2, sigla_value varchar(255), simb_rot float4, sistema_geodesico_code int2, sistema_geodesico_value varchar(255), situacao_em_poligono_code int2, situacao_em_poligono_value varchar(255), situacao_fisica_code int2, situacao_fisica_value varchar(255), situacao_marco_code int2, situacao_marco_value varchar(255), sobreposto_code int2,
      sobreposto_transportes_code int2, sobreposto_transportes_value varchar(255), sobreposto_value varchar(255), subfase_id int4, sujeito_inundacao_code int2, sujeito_inundacao_value varchar(255), suprimir_bandeira_code int2, suprimir_bandeira_value varchar(255), suprimir_simbologia_code int2, suprimir_simbologia_value varchar(255), tamanho_txt float4, texto_edicao varchar(255), tipo_code int2, tipo_elemento_viario_code int2, tipo_elemento_viario_value varchar(255), tipo_exposicao_code int2, tipo_exposicao_value varchar(255), tipo_grid varchar(255), tipo_produto_code int2, tipo_produto_value varchar(255), tipo_ref_code int2, tipo_ref_value varchar(255), tipo_value varchar(255), trafego_code int2, trafego_value varchar(255), uso_pista_code int2, uso_pista_value varchar(255), visivel_code int2, visivel_value varchar(255)
    -> Deaggregator_4
Deaggregator_4
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Clipper_2 [CANDIDATE]
    DEAGGREGATED -> UniqueIdentifierGenerator
Note: 100k
aux_moldura_100k_a (reader POSTGIS_2)
    attributes: id uuid, nome varchar(255), mi varchar(255), inom varchar(255), observacao varchar(255), administracao_code int2, administracao_value varchar(255), altitude float4, altitude_geometrica varchar(255), altitude_ortometrica varchar(255), altura float4, ancora_horizontal_code int2, ancora_horizontal_value varchar(255), ancora_vertical_code int2, ancora_vertical_value varchar(255), assentamento_precario_code int2, assentamento_precario_value varchar(255), bitola_code int2, bitola_value varchar(255), canteiro_divisorio_code int2, canteiro_divisorio_value varchar(255), cod_ponto varchar(255), concessionaria varchar(255), config_comprimento_simb_code int2, config_comprimento_simb_value varchar(255), cor varchar(255), corrigido_code int2, corrigido_value varchar(255), cota int4, cota_comprovada_code int2,
      cota_comprovada_value varchar(255), cota_mais_alta_code int2, cota_mais_alta_value varchar(255), dentro_massa_dagua_code int2, dentro_massa_dagua_value varchar(255), depressao_code int2, depressao_value varchar(255), descricao varchar(255), desloc float4, direcao varchar(255), direcao_fixada_code int2, direcao_fixada_value varchar(255), eletrificada_code int2, eletrificada_value varchar(255), em_arruamento_code int2, em_arruamento_value varchar(255), em_galeria_bueiro_code int2, em_galeria_bueiro_value varchar(255), espacamento float4, estilo_fonte varchar(255), exibir_lado_simbologia_code int2, exibir_lado_simbologia_value varchar(255), exibir_linha_rotulo_code int2, exibir_linha_rotulo_value varchar(255), exibir_ponta_simbologia_code int2, exibir_ponta_simbologia_value varchar(255), exibir_rotulo_aproximado_code int2, exibir_rotulo_aproximado_value varchar(255), finalidade_code int2, finalidade_value varchar(255),
      forma_extracao_code int2, forma_extracao_value varchar(255), geometria_aproximada_code int2, geometria_aproximada_value varchar(255), indice_code int2, indice_value varchar(255), jurisdicao_code int2, jurisdicao_value varchar(255), justificativa varchar(255), justificativa_txt_code int2, justificativa_txt_value varchar(255), label_x float4, label_y float4, largura_simbologia float4, latitude varchar(255), longitude varchar(255), material_construcao_code int2, material_construcao_elemento_viario_code int2, material_construcao_elemento_viario_value varchar(255), material_construcao_value varchar(255), modal_uso_code int2, modal_uso_value varchar(255), nome_elemento_viario varchar(255), nr_faixas varchar(255), nr_linhas_code int2, nr_linhas_value varchar(255), nr_pistas varchar(255), numero varchar(255), ordem_simbologia int4, orgao_responsavel varchar(255),
      populacao int4, posicao_pista_code int2, posicao_pista_elemento_viario_code int2, posicao_pista_elemento_viario_value varchar(255), posicao_pista_value varchar(255), posicao_relativa_code int2, posicao_relativa_value varchar(255), posicao_rotulo_code int2, posicao_rotulo_value varchar(255), referencial_altim_code int2, referencial_altim_value varchar(255), referencial_grav_code int2, referencial_grav_value varchar(255), regime_code int2, regime_value varchar(255), revestimento_code int2, revestimento_value varchar(255), sigla varchar(255), sigla_code int2, sigla_value varchar(255), simb_rot float4, sistema_geodesico_code int2, sistema_geodesico_value varchar(255), situacao_em_poligono_code int2, situacao_em_poligono_value varchar(255), situacao_fisica_code int2, situacao_fisica_value varchar(255), situacao_marco_code int2, situacao_marco_value varchar(255), sobreposto_code int2,
      sobreposto_transportes_code int2, sobreposto_transportes_value varchar(255), sobreposto_value varchar(255), subfase_id int4, sujeito_inundacao_code int2, sujeito_inundacao_value varchar(255), suprimir_bandeira_code int2, suprimir_bandeira_value varchar(255), suprimir_simbologia_code int2, suprimir_simbologia_value varchar(255), tamanho_txt float4, texto_edicao varchar(255), tipo_code int2, tipo_elemento_viario_code int2, tipo_elemento_viario_value varchar(255), tipo_exposicao_code int2, tipo_exposicao_value varchar(255), tipo_grid varchar(255), tipo_produto_code int2, tipo_produto_value varchar(255), tipo_ref_code int2, tipo_ref_value varchar(255), tipo_value varchar(255), trafego_code int2, trafego_value varchar(255), uso_pista_code int2, uso_pista_value varchar(255), visivel_code int2, visivel_value varchar(255)
    -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Tester
Tester
    BOOL_OP = OR
    TEST_CLAUSE = TEST @Value(fme_feature_type) = edgv.aux_moldura_100k_a
    TEST_MODE = TEST
    PASSED -> Clipper [CLIPPER]
    PASSED -> Clipper_2 [CLIPPER]
    FAILED -> Clipper [CANDIDATE]
Clipper_2
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> StringReplacer
StringReplacer
    CASE = NO
    FIND_TEXT = _250k_
    NO_MATCH = _FME_NO_OP_
    REGEXP = NO
    REPLACE_TEXT = _100k_
    SRC_ATTRS = fme_feature_type
    -> Deaggregator_2
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryValidator
GeometryValidator
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK OGC_SIMPLE_CHECK LEGACY_OGC]No]FME_CONTROLLER_QUERY_FILE]transformers/dependencies/geometryvalidator8/OGC_SIMPLE_CHECK.fme]FME_CONTROLLER_CHOICE]OGC_SIMPLE_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> Deaggregator_3
    FAILED -> Deaggregator_3
    REPAIRED -> Deaggregator_3
Deaggregator_3
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Clipper_4 [CANDIDATE]
    DEAGGREGATED -> UniqueIdentifierGenerator
Note: 50k
aux_moldura_50k_a (reader POSTGIS_3)
    attributes: id uuid, nome varchar(255), mi varchar(255), inom varchar(255), observacao varchar(255), administracao_code int2, administracao_value varchar(255), altitude float4, altitude_geometrica varchar(255), altitude_ortometrica varchar(255), altura float4, ancora_horizontal_code int2, ancora_horizontal_value varchar(255), ancora_vertical_code int2, ancora_vertical_value varchar(255), assentamento_precario_code int2, assentamento_precario_value varchar(255), bitola_code int2, bitola_value varchar(255), canteiro_divisorio_code int2, canteiro_divisorio_value varchar(255), cod_ponto varchar(255), concessionaria varchar(255), config_comprimento_simb_code int2, config_comprimento_simb_value varchar(255), cor varchar(255), corrigido_code int2, corrigido_value varchar(255), cota int4, cota_comprovada_code int2,
      cota_comprovada_value varchar(255), cota_mais_alta_code int2, cota_mais_alta_value varchar(255), dentro_massa_dagua_code int2, dentro_massa_dagua_value varchar(255), depressao_code int2, depressao_value varchar(255), descricao varchar(255), desloc float4, direcao varchar(255), direcao_fixada_code int2, direcao_fixada_value varchar(255), eletrificada_code int2, eletrificada_value varchar(255), em_arruamento_code int2, em_arruamento_value varchar(255), em_galeria_bueiro_code int2, em_galeria_bueiro_value varchar(255), espacamento float4, estilo_fonte varchar(255), exibir_lado_simbologia_code int2, exibir_lado_simbologia_value varchar(255), exibir_linha_rotulo_code int2, exibir_linha_rotulo_value varchar(255), exibir_ponta_simbologia_code int2, exibir_ponta_simbologia_value varchar(255), exibir_rotulo_aproximado_code int2, exibir_rotulo_aproximado_value varchar(255), finalidade_code int2, finalidade_value varchar(255),
      forma_extracao_code int2, forma_extracao_value varchar(255), geometria_aproximada_code int2, geometria_aproximada_value varchar(255), indice_code int2, indice_value varchar(255), jurisdicao_code int2, jurisdicao_value varchar(255), justificativa varchar(255), justificativa_txt_code int2, justificativa_txt_value varchar(255), label_x float4, label_y float4, largura_simbologia float4, latitude varchar(255), longitude varchar(255), material_construcao_code int2, material_construcao_elemento_viario_code int2, material_construcao_elemento_viario_value varchar(255), material_construcao_value varchar(255), modal_uso_code int2, modal_uso_value varchar(255), nome_elemento_viario varchar(255), nr_faixas varchar(255), nr_linhas_code int2, nr_linhas_value varchar(255), nr_pistas varchar(255), numero varchar(255), ordem_simbologia int4, orgao_responsavel varchar(255),
      populacao int4, posicao_pista_code int2, posicao_pista_elemento_viario_code int2, posicao_pista_elemento_viario_value varchar(255), posicao_pista_value varchar(255), posicao_relativa_code int2, posicao_relativa_value varchar(255), posicao_rotulo_code int2, posicao_rotulo_value varchar(255), referencial_altim_code int2, referencial_altim_value varchar(255), referencial_grav_code int2, referencial_grav_value varchar(255), regime_code int2, regime_value varchar(255), revestimento_code int2, revestimento_value varchar(255), sigla varchar(255), sigla_code int2, sigla_value varchar(255), simb_rot float4, sistema_geodesico_code int2, sistema_geodesico_value varchar(255), situacao_em_poligono_code int2, situacao_em_poligono_value varchar(255), situacao_fisica_code int2, situacao_fisica_value varchar(255), situacao_marco_code int2, situacao_marco_value varchar(255), sobreposto_code int2,
      sobreposto_transportes_code int2, sobreposto_transportes_value varchar(255), sobreposto_value varchar(255), subfase_id int4, sujeito_inundacao_code int2, sujeito_inundacao_value varchar(255), suprimir_bandeira_code int2, suprimir_bandeira_value varchar(255), suprimir_simbologia_code int2, suprimir_simbologia_value varchar(255), tamanho_txt float4, texto_edicao varchar(255), tipo_code int2, tipo_elemento_viario_code int2, tipo_elemento_viario_value varchar(255), tipo_exposicao_code int2, tipo_exposicao_value varchar(255), tipo_grid varchar(255), tipo_produto_code int2, tipo_produto_value varchar(255), tipo_ref_code int2, tipo_ref_value varchar(255), tipo_value varchar(255), trafego_code int2, trafego_value varchar(255), uso_pista_code int2, uso_pista_value varchar(255), visivel_code int2, visivel_value varchar(255)
    -> Deaggregator_7
Deaggregator_7
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Tester_2
Tester_2
    BOOL_OP = OR
    TEST_CLAUSE = TEST @Value(fme_feature_type) = edgv.aux_moldura_50k_a
    TEST_MODE = TEST
    PASSED -> Clipper_3 [CLIPPER]
    PASSED -> Clipper_4 [CLIPPER]
    FAILED -> Clipper_3 [CANDIDATE]
Clipper_4
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> StringReplacer_2
StringReplacer_2
    CASE = NO
    FIND_TEXT = _100k_
    NO_MATCH = _FME_NO_OP_
    REGEXP = NO
    REPLACE_TEXT = _50k_
    SRC_ATTRS = fme_feature_type
    -> Deaggregator_8
Clipper_3
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Deaggregator_8
Deaggregator_8
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryValidator_3
GeometryValidator_3
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK OGC_SIMPLE_CHECK LEGACY_OGC]No]FME_CONTROLLER_QUERY_FILE]transformers/dependencies/geometryvalidator8/OGC_SIMPLE_CHECK.fme]FME_CONTROLLER_CHOICE]OGC_SIMPLE_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> Deaggregator_9
    FAILED -> Deaggregator_9
    REPAIRED -> Deaggregator_9
Deaggregator_9
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Clipper_6 [CANDIDATE]
    DEAGGREGATED -> UniqueIdentifierGenerator
Note: 25k
aux_moldura_25k_a (reader POSTGIS_4)
    attributes: id uuid, nome varchar(255), mi varchar(255), inom varchar(255), observacao varchar(255), administracao_code int2, administracao_value varchar(255), altitude float4, altitude_geometrica varchar(255), altitude_ortometrica varchar(255), altura float4, ancora_horizontal_code int2, ancora_horizontal_value varchar(255), ancora_vertical_code int2, ancora_vertical_value varchar(255), assentamento_precario_code int2, assentamento_precario_value varchar(255), bitola_code int2, bitola_value varchar(255), canteiro_divisorio_code int2, canteiro_divisorio_value varchar(255), cod_ponto varchar(255), concessionaria varchar(255), config_comprimento_simb_code int2, config_comprimento_simb_value varchar(255), cor varchar(255), corrigido_code int2, corrigido_value varchar(255), cota int4, cota_comprovada_code int2,
      cota_comprovada_value varchar(255), cota_mais_alta_code int2, cota_mais_alta_value varchar(255), dentro_massa_dagua_code int2, dentro_massa_dagua_value varchar(255), depressao_code int2, depressao_value varchar(255), descricao varchar(255), desloc float4, direcao varchar(255), direcao_fixada_code int2, direcao_fixada_value varchar(255), eletrificada_code int2, eletrificada_value varchar(255), em_arruamento_code int2, em_arruamento_value varchar(255), em_galeria_bueiro_code int2, em_galeria_bueiro_value varchar(255), espacamento float4, estilo_fonte varchar(255), exibir_lado_simbologia_code int2, exibir_lado_simbologia_value varchar(255), exibir_linha_rotulo_code int2, exibir_linha_rotulo_value varchar(255), exibir_ponta_simbologia_code int2, exibir_ponta_simbologia_value varchar(255), exibir_rotulo_aproximado_code int2, exibir_rotulo_aproximado_value varchar(255), finalidade_code int2, finalidade_value varchar(255),
      forma_extracao_code int2, forma_extracao_value varchar(255), geometria_aproximada_code int2, geometria_aproximada_value varchar(255), indice_code int2, indice_value varchar(255), jurisdicao_code int2, jurisdicao_value varchar(255), justificativa varchar(255), justificativa_txt_code int2, justificativa_txt_value varchar(255), label_x float4, label_y float4, largura_simbologia float4, latitude varchar(255), longitude varchar(255), material_construcao_code int2, material_construcao_elemento_viario_code int2, material_construcao_elemento_viario_value varchar(255), material_construcao_value varchar(255), modal_uso_code int2, modal_uso_value varchar(255), nome_elemento_viario varchar(255), nr_faixas varchar(255), nr_linhas_code int2, nr_linhas_value varchar(255), nr_pistas varchar(255), numero varchar(255), ordem_simbologia int4, orgao_responsavel varchar(255),
      populacao int4, posicao_pista_code int2, posicao_pista_elemento_viario_code int2, posicao_pista_elemento_viario_value varchar(255), posicao_pista_value varchar(255), posicao_relativa_code int2, posicao_relativa_value varchar(255), posicao_rotulo_code int2, posicao_rotulo_value varchar(255), referencial_altim_code int2, referencial_altim_value varchar(255), referencial_grav_code int2, referencial_grav_value varchar(255), regime_code int2, regime_value varchar(255), revestimento_code int2, revestimento_value varchar(255), sigla varchar(255), sigla_code int2, sigla_value varchar(255), simb_rot float4, sistema_geodesico_code int2, sistema_geodesico_value varchar(255), situacao_em_poligono_code int2, situacao_em_poligono_value varchar(255), situacao_fisica_code int2, situacao_fisica_value varchar(255), situacao_marco_code int2, situacao_marco_value varchar(255), sobreposto_code int2,
      sobreposto_transportes_code int2, sobreposto_transportes_value varchar(255), sobreposto_value varchar(255), subfase_id int4, sujeito_inundacao_code int2, sujeito_inundacao_value varchar(255), suprimir_bandeira_code int2, suprimir_bandeira_value varchar(255), suprimir_simbologia_code int2, suprimir_simbologia_value varchar(255), tamanho_txt float4, texto_edicao varchar(255), tipo_code int2, tipo_elemento_viario_code int2, tipo_elemento_viario_value varchar(255), tipo_exposicao_code int2, tipo_exposicao_value varchar(255), tipo_grid varchar(255), tipo_produto_code int2, tipo_produto_value varchar(255), tipo_ref_code int2, tipo_ref_value varchar(255), tipo_value varchar(255), trafego_code int2, trafego_value varchar(255), uso_pista_code int2, uso_pista_value varchar(255), visivel_code int2, visivel_value varchar(255)
    -> Deaggregator_5
Deaggregator_5
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Tester_3
Tester_3
    BOOL_OP = OR
    TEST_CLAUSE = TEST @Value(fme_feature_type) = edgv.aux_moldura_25k_a
    TEST_MODE = TEST
    PASSED -> Clipper_5 [CLIPPER]
    PASSED -> Clipper_6 [CLIPPER]
    FAILED -> Clipper_5 [CANDIDATE]
Clipper_6
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> StringReplacer_3
StringReplacer_3
    CASE = NO
    FIND_TEXT = _100k_
    NO_MATCH = _FME_NO_OP_
    REGEXP = NO
    REPLACE_TEXT = _50k_
    SRC_ATTRS = fme_feature_type
    -> Deaggregator_6
Clipper_5
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Deaggregator_6
Deaggregator_6
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryValidator_2
GeometryValidator_2
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK OGC_SIMPLE_CHECK LEGACY_OGC]No]FME_CONTROLLER_QUERY_FILE]transformers/dependencies/geometryvalidator8/OGC_SIMPLE_CHECK.fme]FME_CONTROLLER_CHOICE]OGC_SIMPLE_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> Deaggregator_10
    FAILED -> Deaggregator_10
    REPAIRED -> Deaggregator_10
Deaggregator_10
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> UniqueIdentifierGenerator
UniqueIdentifierGenerator
    UUID_ATTR = id
    UUID_FORMAT = UUID_ONLY
    -> Aggregator
Aggregator
    ACCUM_ATTRS_NAME = Use Attributes From One Feature
    AGGREGATE_TYPE = Homogeneous Collection (If Possible)
    GROUP_BY = id
    MODE = Geometry - Assemble One Level
    SEP = ,
    AGGREGATE -> Table1 (writer POSTGIS_5)
Table1 (writer POSTGIS_5)
