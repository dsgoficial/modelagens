FME workspace conversao_postgis213_shp213.fmw

Parameters:
- SourceDataset_POSTGIS = gothic_25k_31981_edgv213v1   # Database PG
- HOST_POSTGIS = 10.25.163.12   # Host PG
- PORT_POSTGIS = 5432   # Port PG
- USER_NAME_POSTGIS = postgres   # Username PG
- PASSWORD_POSTGIS =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   # Password PG
- direcao = ida   # Direção do mapeamento
- JsonMapeamento = E:\DINIZ\3_Desenvolvimento\modelagens\conversao_modelagens\arquivos_mapeamento\conversao_pg-edgv-213_shp-edgv-213.json   # Arquivo de mapeamento
- SourceDataset_ESRISHAPE =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   # SHPs de referência
- DestDataset_ESRISHAPE = C:\Users\diniz.1CGEO.000\Downloads\TESTE_EXPORT   # Pasta destino dos SHP
- FEATURE_TYPES_2 =
- FEATURE_TYPES = cb.adm_area_pub_civil_a cb.adm_area_pub_militar_a cb.adm_descontinuidade_geometrica_a cb.adm_descontinuidade_geometrica_l cb.adm_descontinuidade_geometrica_p cb.adm_edif_pub_civil_a cb.adm_edif_pub_civil_p cb.adm_edif_pub_militar_a cb.adm_edif_pub_militar_p cb.adm_posto_fiscal_a cb.adm_posto_fiscal_p cb.adm_posto_pol_rod_a cb.adm_posto_pol_rod_p cb.asb_area_abast_agua_a cb.asb_area_saneamento_a cb.asb_cemiterio_a cb.asb_cemiterio_p cb.asb_dep_abast_agua_a cb.asb_dep_abast_agua_p cb.asb_dep_saneamento_a cb.asb_dep_saneamento_p cb.asb_descontinuidade_geometrica_a cb.asb_descontinuidade_geometrica_l cb.asb_descontinuidade_geometrica_p cb.asb_edif_abast_agua_a cb.asb_edif_abast_agua_p cb.asb_edif_saneamento_a cb.asb_edif_saneamento_p cb.aux_moldura_a cb.aux_objeto_desconhecido_a cb.aux_objeto_desconhecido_l cb.aux_objeto_desconhecido_p cb.eco_area_agrop_ext_veg_pesca_a cb.eco_area_comerc_serv_a cb.eco_area_ext_mineral_a cb.eco_area_industrial_a cb.eco_deposito_geral_a cb.eco_deposito_geral_p cb.eco_descontinuidade_geometrica_a cb.eco_descontinuidade_geometrica_l cb.eco_descontinuidade_geometrica_p cb.eco_edif_agrop_ext_veg_pesca_a cb.eco_edif_agrop_ext_veg_pesca_p cb.eco_edif_comerc_serv_a cb.eco_edif_comerc_serv_p cb.eco_edif_ext_mineral_a cb.eco_edif_ext_mineral_p cb.eco_edif_industrial_a cb.eco_edif_industrial_p cb.eco_equip_agropec_a cb.eco_equip_agropec_l cb.eco_equip_agropec_p cb.eco_ext_mineral_a cb.eco_ext_mineral_p cb.eco_plataforma_a cb.eco_plataforma_p cb.edu_area_ensino_a cb.edu_area_lazer_a cb.edu_area_religiosa_a cb.edu_area_ruinas_a cb.edu_arquibancada_a cb.edu_arquibancada_p cb.edu_campo_quadra_a cb.edu_campo_quadra_p cb.edu_coreto_tribuna_a cb.edu_coreto_tribuna_p cb.edu_descontinuidade_geometrica_a cb.edu_descontinuidade_geometrica_l cb.edu_descontinuidade_geometrica_p cb.edu_edif_const_lazer_a cb.edu_edif_const_lazer_p cb.edu_edif_const_turistica_a cb.edu_edif_const_turistica_p cb.edu_edif_ensino_a cb.edu_edif_ensino_p cb.edu_edif_religiosa_a cb.edu_edif_religiosa_p cb.edu_piscina_a cb.edu_pista_competicao_l cb.edu_ruina_a cb.edu_ruina_p cb.enc_antena_comunic_p cb.enc_area_comunicacao_a cb.enc_area_energia_eletrica_a cb.enc_descontinuidade_geometrica_a cb.enc_descontinuidade_geometrica_l cb.enc_descontinuidade_geometrica_p cb.enc_edif_comunic_a cb.enc_edif_comunic_p cb.enc_edif_energia_a cb.enc_edif_energia_p cb.enc_est_gerad_energia_eletr_a cb.enc_est_gerad_energia_eletr_l cb.enc_est_gerad_energia_eletr_p cb.enc_grupo_transformadores_a cb.enc_grupo_transformadores_p cb.enc_hidreletrica_a cb.enc_hidreletrica_l cb.enc_hidreletrica_p cb.enc_ponto_trecho_energia_p cb.enc_termeletrica_a cb.enc_termeletrica_p cb.enc_torre_comunic_p cb.enc_torre_energia_p cb.enc_trecho_comunic_l cb.enc_trecho_energia_l cb.enc_zona_linhas_energia_com_a cb.hid_area_umida_a cb.hid_bacia_hidrografica_a cb.hid_banco_areia_a cb.hid_banco_areia_l cb.hid_barragem_a cb.hid_barragem_l cb.hid_barragem_p cb.hid_comporta_l cb.hid_comporta_p cb.hid_confluencia_p cb.hid_corredeira_a cb.hid_corredeira_l cb.hid_corredeira_p cb.hid_descontinuidade_geometrica_a cb.hid_descontinuidade_geometrica_l cb.hid_descontinuidade_geometrica_p cb.hid_fonte_dagua_p cb.hid_foz_maritima_a cb.hid_foz_maritima_l cb.hid_foz_maritima_p cb.hid_ilha_a cb.hid_ilha_l cb.hid_ilha_p cb.hid_limite_massa_dagua_l cb.hid_massa_dagua_a cb.hid_natureza_fundo_a cb.hid_natureza_fundo_l cb.hid_natureza_fundo_p cb.hid_ponto_drenagem_p cb.hid_ponto_inicio_drenagem_p cb.hid_quebramar_molhe_a cb.hid_quebramar_molhe_l cb.hid_queda_dagua_a cb.hid_queda_dagua_l cb.hid_queda_dagua_p cb.hid_recife_a cb.hid_recife_l cb.hid_recife_p cb.hid_reservatorio_hidrico_a cb.hid_rocha_em_agua_a cb.hid_rocha_em_agua_p cb.hid_sumidouro_vertedouro_p cb.hid_terreno_suj_inundacao_a cb.hid_trecho_drenagem_l cb.hid_trecho_massa_dagua_a cb.lim_area_de_litigio_a cb.lim_area_de_propriedade_particular_a cb.lim_area_desenv_controle_a cb.lim_area_desenv_controle_p cb.lim_area_uso_comunitario_a cb.lim_area_uso_comunitario_p cb.lim_bairro_a cb.lim_delimitacao_fisica_l cb.lim_descontinuidade_geometrica_a cb.lim_descontinuidade_geometrica_l cb.lim_descontinuidade_geometrica_p cb.lim_distrito_a cb.lim_limite_area_especial_l cb.lim_limite_intra_munic_adm_l cb.lim_limite_operacional_l cb.lim_limite_particular_l cb.lim_limite_politico_adm_l cb.lim_linha_de_limite_l cb.lim_marco_de_limite_p cb.lim_municipio_a cb.lim_outras_unid_protegidas_a cb.lim_outras_unid_protegidas_p cb.lim_outros_limites_oficiais_l cb.lim_pais_a cb.lim_regiao_administrativa_a cb.lim_sub_distrito_a cb.lim_terra_indigena_a cb.lim_terra_indigena_p cb.lim_terra_publica_a cb.lim_terra_publica_p cb.lim_unidade_conserv_nao_snuc_a cb.lim_unidade_conserv_nao_snuc_p cb.lim_unidade_federacao_a cb.lim_unidade_protecao_integral_a cb.lim_unidade_protecao_integral_p cb.lim_unidade_uso_sustentavel_a cb.lim_unidade_uso_sustentavel_p cb.loc_aglom_rural_de_ext_urbana_p cb.loc_aglomerado_rural_isolado_p cb.loc_area_edificada_a cb.loc_area_habitacional_a cb.loc_area_urbana_isolada_a cb.loc_capital_p cb.loc_cidade_p cb.loc_descontinuidade_geometrica_a cb.loc_descontinuidade_geometrica_l cb.loc_descontinuidade_geometrica_p cb.loc_edif_habitacional_a cb.loc_edif_habitacional_p cb.loc_edificacao_a cb.loc_edificacao_p cb.loc_hab_indigena_a cb.loc_hab_indigena_p cb.loc_nome_local_p cb.loc_vila_p cb.pto_area_est_med_fenom_a cb.pto_descontinuidade_geometrica_a cb.pto_descontinuidade_geometrica_l cb.pto_descontinuidade_geometrica_p cb.pto_edif_constr_est_med_fen_a cb.pto_edif_constr_est_med_fen_p cb.pto_pto_controle_p cb.pto_pto_est_med_fenomenos_p cb.pto_pto_ref_geod_topo_p cb.rel_alter_fisiog_antropica_a cb.rel_alter_fisiog_antropica_l cb.rel_curva_batimetrica_l cb.rel_curva_nivel_l cb.rel_descontinuidade_geometrica_a cb.rel_descontinuidade_geometrica_l cb.rel_descontinuidade_geometrica_p cb.rel_dolina_a cb.rel_dolina_p cb.rel_duna_a cb.rel_duna_p cb.rel_elemento_fisiog_natural_a cb.rel_elemento_fisiog_natural_l cb.rel_elemento_fisiog_natural_p cb.rel_gruta_caverna_p cb.rel_pico_p cb.rel_ponto_cotado_altimetrico_p cb.rel_ponto_cotado_batimetrico_p cb.rel_rocha_a cb.rel_rocha_p cb.rel_terreno_exposto_a cb.sau_area_saude_a cb.sau_area_servico_social_a cb.sau_descontinuidade_geometrica_a cb.sau_descontinuidade_geometrica_l cb.sau_descontinuidade_geometrica_p cb.sau_edif_saude_a cb.sau_edif_saude_p cb.sau_edif_servico_social_a cb.sau_edif_servico_social_p cb.tra_area_duto_a cb.tra_area_estrut_transporte_a cb.tra_arruamento_l cb.tra_atracadouro_a cb.tra_atracadouro_l cb.tra_atracadouro_p cb.tra_caminho_aereo_l cb.tra_ciclovia_l cb.tra_condutor_hidrico_l cb.tra_cremalheira_l cb.tra_cremalheira_p cb.tra_descontinuidade_geometrica_a cb.tra_descontinuidade_geometrica_l cb.tra_descontinuidade_geometrica_p cb.tra_eclusa_a cb.tra_eclusa_l cb.tra_eclusa_p cb.tra_edif_constr_aeroportuaria_a cb.tra_edif_constr_aeroportuaria_p cb.tra_edif_constr_portuaria_a cb.tra_edif_constr_portuaria_p cb.tra_edif_metro_ferroviaria_a cb.tra_edif_metro_ferroviaria_p cb.tra_edif_rodoviaria_a cb.tra_edif_rodoviaria_p cb.tra_entroncamento_p cb.tra_faixa_seguranca_a cb.tra_fundeadouro_a cb.tra_fundeadouro_l cb.tra_fundeadouro_p cb.tra_funicular_l cb.tra_funicular_p cb.tra_galeria_bueiro_l cb.tra_galeria_bueiro_p cb.tra_girador_ferroviario_p cb.tra_identific_trecho_rod_p cb.tra_local_critico_a cb.tra_local_critico_l cb.tra_local_critico_p cb.tra_obstaculo_navegacao_a cb.tra_obstaculo_navegacao_l cb.tra_obstaculo_navegacao_p cb.tra_passag_elevada_viaduto_l cb.tra_passag_elevada_viaduto_p cb.tra_passagem_nivel_p cb.tra_patio_a cb.tra_patio_p cb.tra_pista_ponto_pouso_a cb.tra_pista_ponto_pouso_l cb.tra_pista_ponto_pouso_p cb.tra_ponte_l cb.tra_ponte_p cb.tra_ponto_duto_p cb.tra_ponto_hidroviario_p cb.tra_ponto_rodoviario_ferrov_p cb.tra_posto_combustivel_a cb.tra_posto_combustivel_p cb.tra_sinalizacao_p cb.tra_travessia_l cb.tra_travessia_p cb.tra_travessia_pedestre_l cb.tra_travessia_pedestre_p cb.tra_trecho_duto_l cb.tra_trecho_ferroviario_l cb.tra_trecho_hidroviario_l cb.tra_trecho_rodoviario_l cb.tra_trilha_picada_l cb.tra_tunel_l cb.tra_tunel_p cb.veg_brejo_pantano_a cb.veg_caatinga_a cb.veg_campinarana_a cb.veg_campo_a cb.veg_cerrado_cerradao_a cb.veg_descontinuidade_geometrica_a cb.veg_descontinuidade_geometrica_l cb.veg_descontinuidade_geometrica_p cb.veg_estepe_a cb.veg_floresta_a cb.veg_macega_chavascal_a cb.veg_mangue_a cb.veg_veg_area_contato_a cb.veg_veg_cultivada_a cb.veg_veg_restinga_a

Readers:
- POSTGIS_1: POSTGIS from $(SourceDataset_POSTGIS)
- ESRISHAPE_1: ESRISHAPE from $(SourceDataset_ESRISHAPE)

Writers:
- ESRISHAPE_2: ESRISHAPE to $(DestDataset_ESRISHAPE)

Note: PostGIS EDGV 2.1.3
adm_area_pub_civil_a (reader POSTGIS_1)
    attributes: id serial, geometriaaproximada int2, tipoedifmil int2, nascente int2, namaximomaximorum int4, obs varchar(255), mattransp int2, tipocemiterio int2, coletiva int2, tipoprodutoresiduo int2, codigootto int4, tipotorre int2, relacionado int2, historicomodificacao varchar(255), classificacaoporte int2, rede int2, tipopostofisc int2, orgaoenteresp varchar(255), potenciafiscalizada float4, perimetrooficial float4, canteirodivisorio int2, tipoobst int2, vaovertical float4, latitude varchar(255), tipoptoestmed int2, tipoptoenergia int2, tipotunel int2, profundidademedia float4, nrdutos int4, denso int2,
      classe varchar(255), pesosuportmaximo float4, especie int2, tiposinal int2, tipotravessia int2, procextracao int2, codigoestacao varchar(255), tipolimpol int2, tipooutlimofic int2, regime int2, nomeabrev varchar(255), referencialaltim int2, tipoedifrod int2, codtrechoferrov varchar(255), tipoestgerad int2, revestimento int2, obssituacao varchar(255), situacaoespacial int2, tipoclassecnae int2, tipomarcolim int2, larguramedia float4, matconstr int2, tipoilha int2, emarruamento int2, dentrodepoligono int2, formaextracao int2, sigla varchar(255), destinadoa int2, caladomax float4, tiporecife int2,
      extensao float4, tipotrechoferrov int2, causa int2, coincidecomdentrode int2, classificacao varchar(255), isolada int2, velocidademedcorrente float4, situacaofisica int2, tipocapital int2, codprojeto varchar(255), espessuradap float4, tipooutunidprot int2, tipoedifagropec int2, destinacaofundeadouro int2, cotacomprovada int2, nrfaixas int4, tipofontedagua int2, especiepredominante int2, arranjofases varchar(255), espessalgas int2, tipodivisaocnae int2, tipogrutacaverna int2, altura float4, nrpistas int4, tipolimareaesp int2, posicaorelativa int2, identificador varchar(255), codestacao varchar(255), tipodepgeral int2, tipolimintramun int2,
      tipousoedif int2, tiporesiduo int2, codponto varchar(255), atolegal varchar(255), periodicidadeinunda varchar(255), tipotravessiaped int2, caladomaxseca float4, destenergelet int2, homologacao int2, datavisita varchar(255), alturalamina float4, tipoassociado int2, cultivopredominante int2, espacamentoindividuos float4, tipoatracad int2, altitudeortometrica float4, gabhorizsup float4, tipocombustivel int2, trafego int2, largura float4, gabvertsup float4, usopista int2, nrlinhas int2, nome varchar(255), extensaotrecho float4, areaoficial varchar(255), modaluso int2, tipopista int2, tipocampo int2, administracao int2,
      tipoaglomrurisol int2, setor int2, posicaopista int2, anocriacao varchar(255), areaoficialha float4, geracao int2, tipousocaminhoaer int2, tipopassagviad int2, tipolavoura int2, alturaestimada float4, compartilhado int2, nivelotto int4, tiporocha int2, tipoponte int2, tipoexposicao int2, codigohidreletrica varchar(255), atividade int2, indice int2, tipotrechoduto int2, navegabilidade int2, tipomacchav int2, numcircuitos int4, tipocaminhoaereo int2, tipocondutor int2, tipoptocontrole int2, situacaoemagua int2, tipotrechocomunic int2, qualidagua int2, tipoedifrelig int2, tipoextmin int2,
      tipodepabast int2, tipolimoper int2, datasituacaojuridica date, tipoedifturist int2, ensino int2, salinidade int2, tipomassadagua int2, materializado int2, tipounidusosust int2, multimodal int2, tipoedifcivil int2, tipoedifaero int2, jurisdicao int2, tipoterrexp int2, emduto int2, tipotrechorod int2, situacaoagua int2, tipoequipagropec int2, funcaoedifmetroferrov int2, outrarefalt varchar(255), vaolivrehoriz float4, tipocampoquadra int2, cargasuportmaxima float4, sistemageodesico int2, cota int4, eletrificada int2, nivelatencao int2, tipoalterantrop int2, tipoplataforma int2, descricao varchar(255),
      unidadevolume int2, mi varchar(255), tensaoeletrica float4, posicaoreledific int2, residuo int2, namaximooperacional int4, alturamediaindividuos float4, tiposumvert int2, finalidade int2, tipoedifabast int2, tiposecaocnae int2, materialpredominante int2, usoprincipal int2, modalidade int2, operacional int2, tipopostopol int2, religiao varchar(255), tipoareausocomun int2, proximidade int2, tipoptorefgeodtopo int2, grupoetnico varchar(255), escala varchar(255), valorvolume float4, situacaocosta int2, geocodigo varchar(255), terreno int2, outrarefplan varchar(255), tipoediflazer int2, causaexposicao int2, chamine int2,
      tipotrechomassa int2, tipoquebramolhe int2, profundidade int4, referencialgrav int2, eixoprincipal int2, tipocerr int2, tipoedifcomunic int2, tipoconteudo int2, potenciaoutorgada float4, nometi varchar(255), tipoareaumida int2, tipobanco int2, ocorrenciaem int2, tipopocomina int2, caracteristicafloresta int2, combrenovavel int2, tipoelemnat int2, tipodelimfis int2, tratamento int2, concessionaria varchar(255), capaccarga float4, anodereferencia int4, codtrechorodov varchar(255), alturamediamargem float4, codiso3166 varchar(255), motivodescontinuidade int2, tipobrejopantano int2, tipoedifsaneam int2, orgresp varchar(255), tipoentroncamento int2,
      tipoedifenergia int2, construcao int2, inom varchar(255), tipomaqtermica int2, denominacaoassociada int2, volumeutil int4, situamare int2, tipoedifcomercserv int2, tipodepsaneam int2, bitola int2, tipolimmassa int2, tipoqueda int2, fixa int2, desnivel float4, situacaomarco int2, tipounidprotinteg int2, calado float4, situacaojuridica int2, ovgd int2, tipolocalcrit int2, longitude varchar(255), depressao int2, tiporef int2, antropizada int2, tipoedifport int2
    -> PythonCaller_2
Note: mapeamento
PythonCaller_2
    NEW_ATTRIBUTES = CLASS_NOT_FOUND
    PYTHONSOURCE:
      import fme
      import fmeobjects
      import copy
      import sys
      import os
      import json

      class FeatureProcessor(object):
          def __init__(self):
              self.mappingDict = self.buildFileDict(FME_MacroValues['JsonMapeamento'])
              self.mappingType = FME_MacroValues['direcao']

          def buildFileDict(self, mappingPath):
              with open(mappingPath, 'r', encoding='utf-8') as file:
                  mapDict = json.loads(file.read())
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          featDict[attr] = feature.getAttribute(attr)
                      else:
                          featDict[attr] = None
              if feature.performFunction('@GeometryType()') == 'fme_polygon' or feature.performFunction('@GeometryType()') == 'fme_donut':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              else:
                   featDict["INVALID_GEOM"] = True
              return featDict

          def evaluateExpression(self, featDict, expression):
              return expression["nome_atributo"] in featDict and u"{0}".format(featDict[expression["nome_atributo"]]) == u"{0}".format(expression["valor"])

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "ida":
                  key_attr_origin = "attr_ida"
                  key_attr_destiny = "attr_volta"
                  key_value_origin = "valor_ida"
                  key_value_destiny = "valor_volta"
                  key_default = "atributos_default_ida"
                  key_filter = "filtro_ida"
                  key_class_origin = "classe_ida"
                  key_class_destiny = "classe_volta"
                  key_group_origin = "tupla_ida"
                  key_group_destiny = "tupla_volta"
                  key_affix_origin = "afixo_geom_ida"
                  key_affix_destiny = "afixo_geom_volta"
                  key_schema_origin = "schema_ida"
                  key_schema_destiny = "schema_volta"
                  key_class_affix_origin = "com_afixo_geom_ida"
                  key_class_affix_destiny = "com_afixo_geom_volta"
                  key_class_schema_origin = "com_schema_ida"
                  key_class_schema_destiny = "com_schema_volta"
                  key_agregar = "agregar_geom_ida"
              else:
                  key_attr_origin = "attr_volta"
                  key_attr_destiny = "attr_ida"
                  key_value_origin = "valor_volta"
                  key_value_destiny = "valor_ida"
                  key_default = "atributos_default_volta"
                  key_filter = "filtro_volta"
                  key_class_origin = "classe_volta"
                  key_class_destiny = "classe_ida"
                  key_group_origin = "tupla_volta"
                  key_group_destiny = "tupla_ida"
                  key_affix_origin = "afixo_geom_volta"
                  key_affix_destiny = "afixo_geom_ida"
                  key_schema_origin = "schema_volta"
                  key_schema_destiny = "schema_ida"
                  key_class_affix_origin = "com_afixo_geom_volta"
                  key_class_affix_destiny = "com_afixo_geom_ida"
                  key_class_schema_origin = "com_schema_volta"
                  key_class_schema_destiny = "com_schema_ida"
                  key_agregar = "agregar_geom_volta"

              featDict["fme_feature_type_original"] = featDict["fme_feature_type"]

              if key_schema_origin in self.mappingDict and self.mappingDict[key_schema_origin]:
                  featDict["fme_feature_type"] = featDict["fme_feature_type"][len(self.mappingDict[key_schema_origin])+1:]

              featDict["fme_feature_type_sem_schema"] = featDict["fme_feature_type"]

              if key_affix_origin in self.mappingDict and 'tipo' in self.mappingDict[key_affix_origin] and self.mappingDict[key_affix_origin]['tipo'] == 'sufixo':
                  featDict["fme_feature_type"] = featDict["fme_feature_type"][:-len(self.mappingDict[key_affix_origin][featDict["$GEOM_TYPE"]])]
                  featDict["fme_feature_type_sem_afixo"] = featDict["fme_feature_type_original"][:-len(self.mappingDict[key_affix_origin][featDict["$GEOM_TYPE"]])]

              if key_affix_origin in self.mappingDict and 'tipo' in self.mappingDict[key_affix_origin] and self.mappingDict[key_affix_origin]['tipo'] == 'prefixo':
                  featDict["fme_feature_type"] = featDict["fme_feature_type"][len(self.mappingDict[key_affix_origin][featDict["$GEOM_TYPE"]]):]
                  featDict["fme_feature_type_sem_afixo"] = featDict["fme_feature_type_original"][len(self.mappingDict[key_affix_origin][featDict["$GEOM_TYPE"]]):]

              should_map = False
              for classmap in self.mappingDict['mapeamento_classes']:
                  if "sentido" not in classmap or ("sentido" in classmap and classmap["sentido"] == self.mappingType):
                      if key_class_affix_origin in classmap and classmap[key_class_affix_origin] and key_class_schema_origin in classmap and classmap[key_class_schema_origin]:
                          class_name = featDict["fme_feature_type_original"]
                      elif key_class_affix_origin in classmap and classmap[key_class_affix_origin]:
                          class_name = featDict["fme_feature_type_sem_schema"]
                      elif key_class_schema_origin in classmap and classmap[key_class_schema_origin]:
                          class_name = featDict["fme_feature_type_sem_afixo"]
                      else:
                           class_name = featDict["fme_feature_type"]

                      if classmap[key_class_origin] == class_name:
                          if key_filter in classmap:
                              if not self.evaluateFilter(featDict, classmap[key_filter]):
                                  continue
                          should_map = True
              if not should_map:
                  featDict["CLASS_NOT_FOUND"] = True
                  return featDict

              mappedFeat = copy.deepcopy(featDict)

              if key_default in self.mappingDict:
                  for default in self.mappingDict[key_default]:
                      mappedFeat[default["nome_atributo"]] = default["valor"]

              if 'mapeamento_atributos' in self.mappingDict:
                  for attmap in self.mappingDict['mapeamento_atributos']:
                      if attmap[key_attr_origin] in featDict:
                          mappedFeat[attmap[key_attr_destiny]] = featDict[attmap[key_attr_origin]]
                          if "traducao" in attmap:
                              for valuemap in attmap["traducao"]:
                                  if u"{0}".format(valuemap[key_value_origin]) == u"{0}".format(featDict[attmap[key_attr_origin]]) and ("sentido" not in valuemap or ("sentido" in valuemap and valuemap["sentido"] == self.mappingType)):
                                      mappedFeat[attmap[key_attr_destiny]] = valuemap[key_value_destiny]

              if 'mapeamento_classes' in self.mappingDict:
                  for classmap in self.mappingDict['mapeamento_classes']:
                      if "sentido" not in classmap or ("sentido" in classmap and classmap["sentido"] == self.mappingType):
                          if key_class_affix_origin in classmap and classmap[key_class_affix_origin] and key_class_schema_origin in classmap and classmap[key_class_schema_origin]:
                              class_name = featDict["fme_feature_type_original"]
                          elif key_class_affix_origin in classmap and classmap[key_class_affix_origin]:
                              class_name = featDict["fme_feature_type_sem_schema"]
                          elif key_class_schema_origin in classmap and classmap[key_class_schema_origin]:
                              class_name = featDict["fme_feature_type_sem_afixo"]
                          else:
                              class_name = featDict["fme_feature_type"]

                          if classmap[key_class_origin] == class_name:
                              if key_filter in classmap:
                                  if not self.evaluateFilter(featDict, classmap[key_filter]):
                                      continue

                              mappedFeat["fme_feature_type"] = classmap[key_class_destiny]

                              if key_class_affix_destiny in classmap and classmap[key_class_affix_destiny]:
                                  pass
                              elif key_affix_destiny in self.mappingDict and 'tipo' in self.mappingDict[key_affix_destiny]:
                                  if self.mappingDict[key_affix_destiny]['tipo'] == 'sufixo':
                                      mappedFeat["fme_feature_type"] = mappedFeat["fme_feature_type"] + self.mappingDict[key_affix_destiny][featDict["$GEOM_TYPE"]]

                                  if self.mappingDict[key_affix_destiny]['tipo'] == 'prefixo':
                                      mappedFeat["fme_feature_type"] = self.mappingDict[key_affix_destiny][featDict["$GEOM_TYPE"]] + mappedFeat["fme_feature_type"]

                              if key_class_schema_destiny in classmap and classmap[key_class_schema_destiny]:
                                  pass
                              elif key_schema_destiny in self.mappingDict and self.mappingDict[key_schema_destiny]:
                                  mappedFeat["fme_feature_type"] = self.mappingDict[key_schema_destiny] + '.' + mappedFeat["fme_feature_type"]


                              if key_default in classmap:
                                  for default in classmap[key_default]:
                                      mappedFeat[default["nome_atributo"]] = default["valor"]

                              if "mapeamento_atributos" in classmap:
                                  for attmap in classmap['mapeamento_atributos']:
                                      if attmap[key_attr_origin] in featDict:
                                          if attmap[key_attr_destiny] not in mappedFeat:
                                              mappedFeat[attmap[key_attr_destiny]] = featDict[attmap[key_attr_origin]]
                                          if "traducao" in attmap:
                                              for valuemap in attmap["traducao"]:
                                                  if u"{0}".format(valuemap[key_value_origin]) == u"{0}".format(featDict[attmap[key_attr_origin]]) and ("sentido" not in valuemap or ("sentido" in valuemap and valuemap["sentido"] == self.mappingType)):
                                                      mappedFeat[attmap[key_attr_destiny]] = valuemap[key_value_destiny]

                              if "mapeamento_multiplo" in classmap:
                                  for attmap in classmap['mapeamento_multiplo']:
                                      if "sentido" not in attmap or ("sentido" in attmap and attmap["sentido"] == self.mappingType):
                                          if all([self.evaluateExpression(featDict, condition) for condition in attmap[key_group_origin]]):
                                              for valuemap in attmap[key_group_destiny]:
                                                  if "concatenar" in valuemap and valuemap["concatenar"] and valuemap["nome_atributo"] in mappedFeat and mappedFeat[valuemap["nome_atributo"]]:
                                                      mappedFeat[valuemap["nome_atributo"]] = mappedFeat[valuemap["nome_atributo"]] + ' | ' + valuemap["valor"]
                                                  else:
                                                      mappedFeat[valuemap["nome_atributo"]] = valuemap["valor"]

                              if key_agregar in classmap:
                                  mappedFeat["AGGREGATE_GEOM"] = classmap[key_agregar]
                              elif key_agregar in self.mappingDict:
                                  mappedFeat["AGGREGATE_GEOM"] = self.mappingDict[key_agregar]

                              break

              return mappedFeat

          def mapDictToFeature(self, feat, featDict):
              for attr, value in featDict.items():
                  if value or value == 0:
                      feat.setAttribute(attr, u'{0}'.format(value))
                  else:
                      feat.setAttributeNullWithType(attr,0)
              if "AGGREGATE_GEOM" in featDict and featDict["AGGREGATE_GEOM"]:
                  feat.buildAggregateFeat([feat])
              return feat

          def input(self,feature):
              if feature.performFunction('@GeometryType()') == 'fme_aggregate':
                  features = feature.splitAggregate(True)
              else:
                  features = [feature]
              for simple_feature in features:
                  feat = self.buildFeatureDict(simple_feature)
                  if "INVALID_GEOM" in feat and not feat["INVALID_GEOM"]:
                      simple_feature.setAttribute("INVALID_GEOM", u'True')
                      self.pyoutput(simple_feature)
                      continue

                  outputFeatDict = self.convertFeature(feat)
                  if "CLASS_NOT_FOUND" in outputFeatDict and not outputFeatDict["CLASS_NOT_FOUND"]:
                      simple_feature.setAttribute("CLASS_NOT_FOUND", u'True')
                      self.pyoutput(simple_feature)
                  else:
                      outputFeature = self.mapDictToFeature(simple_feature, outputFeatDict)
                      self.pyoutput(outputFeature)

          def close(self):
              pass
    PYTHONSYMBOL = FeatureProcessor
    -> Tester_4
Note: Teste de mapeamento
Tester_4
    BOOL_OP = OR
    TEST_CLAUSE = TEST @Value(CLASS_NOT_FOUND) = True
    TEST_MODE = TEST
    PASSED -> CLASSE_NAO_ENCONTRADA
    FAILED -> Shapefile1 (writer ESRISHAPE_2)
CLASSE_NAO_ENCONTRADA: Inspector
Shapefile1 (writer ESRISHAPE_2)
Note: SHP EDGV 2.1.3 / utilizado como recurso pro mapeamento dinâmico
ADM_Area_Pub_Civil_A (reader ESRISHAPE_1) [off]
    attributes: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
