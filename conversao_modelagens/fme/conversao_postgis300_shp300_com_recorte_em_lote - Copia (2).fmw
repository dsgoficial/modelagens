FME workspace conversao_postgis300_shp300_com_recorte_em_lote - Copia (2).fmw

Parameters:
- ESPG = 4674
- SourceDataset_POSTGIS = rsrf1_25k_4674_edgv300   # Database

Readers:
- POSTGIS_1: POSTGIS from $(SourceDataset_POSTGIS)

aux_moldura_a (reader POSTGIS_1)
    attributes: id serial, escala varchar(255), inom varchar(255), mi varchar(255), nome varchar(255)
    -> Tester
Tester
    BOOL_OP = COMPOSITE
    COMPOSITE_TEST = 1 AND 2
    TEST_CLAUSE:
      TEST @Value(escala) = Exportar
      TEST @Value(nome) = Lote 3
    TEST_MODE = TEST
    PASSED -> GeometryExtractor
GeometryExtractor
    ATTR = _geometry
    KIND_LONG = OGC Well Known Text
    OGCVERSION = 1.2
    OGC_WKT_PRECISION_DISPLAY = 64-bit
    PREFER_POLYGON_OVER_SURFACE = No
    REMOVE_GEOMETRY = No
    -> AttributeCreator
AttributeCreator
    ATTR_TABLE = SET_TO ewkt = SRID=$(ESPG);@Value(_geometry)
    -> WorkspaceRunner
WorkspaceRunner
    BLOCKING = Yes
    WORKSPACE_FILE = $(FME_MF_DIR)conversao_postgis300_shp300_com_recorte.fmw
    WORKSPACE_PARAMETERS =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
    SUCCEEDED -> WorkspaceRunner_Succeeded
    FAILED -> WorkspaceRunner_Failed
    SUMMARY -> WorkspaceRunner_Summary
WorkspaceRunner_Succeeded: Inspector
WorkspaceRunner_Failed: Inspector
WorkspaceRunner_Summary: Inspector
