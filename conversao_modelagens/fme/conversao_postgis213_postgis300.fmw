FME workspace conversao_postgis213_postgis300.fmw

Parameters:
- JsonMapeamento = C:\Diniz\modelagens\conversao_modelagens\arquivos_mapeamento\conversao_pg-edgv-213_pg-edgv-300.json   # Arquivo de mapeamento
- direcao = ida   # Direção do mapeamento
- SourceDataset_POSTGIS_4 = gothic_25k_31982_edgv213v1   # Database 213
- postgis_sql_where_clause =
- SourceDataset_POSTGIS_3 = gothic_25k_4674_edgv30   # Database
- FEATURE_TYPES = edgv.aer_pista_ponto_pouso_a edgv.aer_pista_ponto_pouso_l edgv.aer_pista_ponto_pouso_p edgv.aux_moldura_a edgv.cbge_area_agropec_ext_vegetal_pesca_a edgv.cbge_area_construida_a edgv.cbge_area_de_propriedade_particular_a edgv.cbge_area_duto_a edgv.cbge_area_habitacional_a edgv.cbge_area_uso_especifico_a edgv.cbge_canteiro_central_a edgv.cbge_canteiro_central_l edgv.cbge_cemiterio_a edgv.cbge_cemiterio_p edgv.cbge_delimitacao_fisica_l edgv.cbge_deposito_geral_a edgv.cbge_deposito_geral_p edgv.cbge_entroncamento_area_a edgv.cbge_espelho_dagua_a edgv.cbge_estacionamento_a edgv.cbge_largo_a edgv.cbge_passeio_a edgv.cbge_passeio_l edgv.cbge_poste_p edgv.cbge_praca_a edgv.cbge_quadra_a edgv.cbge_retorno_l edgv.cbge_retorno_p edgv.cbge_trecho_arruamento_a edgv.cbge_trecho_arruamento_l edgv.dut_galeria_bueiro_l edgv.dut_galeria_bueiro_p edgv.dut_trecho_duto_l edgv.eco_equip_agropec_a edgv.eco_equip_agropec_l edgv.eco_equip_agropec_p edgv.eco_ext_mineral_a edgv.eco_ext_mineral_p edgv.eco_plataforma_a edgv.eco_plataforma_p edgv.edf_banheiro_publico_a edgv.edf_banheiro_publico_p edgv.edf_edif_abast_agua_a edgv.edf_edif_abast_agua_p edgv.edf_edif_agropec_ext_vegetal_pesca_a edgv.edf_edif_agropec_ext_vegetal_pesca_p edgv.edf_edif_comerc_serv_a edgv.edf_edif_comerc_serv_p edgv.edf_edif_comunic_a edgv.edf_edif_comunic_p edgv.edf_edif_constr_aeroportuaria_a edgv.edf_edif_constr_aeroportuaria_p edgv.edf_edif_constr_est_med_fen_a edgv.edf_edif_constr_est_med_fen_p edgv.edf_edif_constr_lazer_a edgv.edf_edif_constr_lazer_p edgv.edf_edif_constr_portuaria_a edgv.edf_edif_constr_portuaria_p edgv.edf_edif_constr_turistica_a edgv.edf_edif_constr_turistica_p edgv.edf_edif_desenv_social_a edgv.edf_edif_desenv_social_p edgv.edf_edif_energia_a edgv.edf_edif_energia_p edgv.edf_edif_ensino_a edgv.edf_edif_ensino_p edgv.edf_edif_ext_mineral_a edgv.edf_edif_ext_mineral_p edgv.edf_edif_industrial_a edgv.edf_edif_industrial_p edgv.edf_edif_metro_ferroviaria_a edgv.edf_edif_metro_ferroviaria_p edgv.edf_edif_policia_a edgv.edf_edif_policia_p edgv.edf_edif_pub_civil_a edgv.edf_edif_pub_civil_p edgv.edf_edif_pub_militar_a edgv.edf_edif_pub_militar_p edgv.edf_edif_religiosa_a edgv.edf_edif_religiosa_p edgv.edf_edif_residencial_a edgv.edf_edif_residencial_p edgv.edf_edif_rodoviaria_a edgv.edf_edif_rodoviaria_p edgv.edf_edif_saneamento_a edgv.edf_edif_saneamento_p edgv.edf_edif_saude_a edgv.edf_edif_saude_p edgv.edf_edificacao_a edgv.edf_edificacao_p edgv.edf_hab_indigena_a edgv.edf_hab_indigena_p edgv.edf_posto_combustivel_a edgv.edf_posto_combustivel_p edgv.edf_posto_fiscal_a edgv.edf_posto_fiscal_p edgv.edf_posto_guarda_municipal_a edgv.edf_posto_guarda_municipal_p edgv.edf_posto_policia_militar_a edgv.edf_posto_policia_militar_p edgv.edf_posto_policia_rod_federal_a edgv.edf_posto_policia_rod_federal_p edgv.edf_representacao_diplomatica_a edgv.edf_representacao_diplomatica_p edgv.emu_acesso_a edgv.emu_acesso_l edgv.emu_acesso_p edgv.emu_ciclovia_l edgv.emu_elevador_a edgv.emu_elevador_l edgv.emu_elevador_p edgv.emu_escadaria_a edgv.emu_escadaria_l edgv.emu_escadaria_p edgv.emu_poste_sinalizacao_p edgv.emu_rampa_a edgv.emu_rampa_l edgv.emu_rampa_p edgv.enc_aerogerador_p edgv.enc_antena_comunic_p edgv.enc_casa_de_forca_p edgv.enc_central_geradora_eolica_a edgv.enc_central_geradora_eolica_p edgv.enc_est_gerad_energia_eletrica_a edgv.enc_est_gerad_energia_eletrica_p edgv.enc_grupo_transformadores_a edgv.enc_grupo_transformadores_p edgv.enc_hidreletrica_a edgv.enc_hidreletrica_l edgv.enc_hidreletrica_p edgv.enc_subest_transm_distrib_energia_eletrica_a edgv.enc_termeletrica_a edgv.enc_termeletrica_p edgv.enc_torre_comunic_p edgv.enc_torre_energia_p edgv.enc_trecho_comunic_l edgv.enc_trecho_energia_l edgv.enc_zona_linhas_energia_comunicacao_a edgv.fer_cremalheira_l edgv.fer_cremalheira_p edgv.fer_girador_ferroviario_p edgv.fer_trecho_ferroviario_l edgv.hdv_atracadouro_terminal_a edgv.hdv_atracadouro_terminal_l edgv.hdv_atracadouro_terminal_p edgv.hdv_eclusa_a edgv.hdv_eclusa_l edgv.hdv_eclusa_p edgv.hdv_fundeadouro_a edgv.hdv_fundeadouro_p edgv.hdv_obstaculo_navegacao_a edgv.hdv_obstaculo_navegacao_l edgv.hdv_obstaculo_navegacao_p edgv.hdv_sinalizacao_p edgv.hdv_trecho_hidroviario_l edgv.hid_area_umida_a edgv.hid_banco_areia_a edgv.hid_barragem_a edgv.hid_barragem_l edgv.hid_barragem_p edgv.hid_canal_a edgv.hid_canal_l edgv.hid_comporta_l edgv.hid_comporta_p edgv.hid_corredeira_a edgv.hid_corredeira_l edgv.hid_corredeira_p edgv.hid_dique_a edgv.hid_dique_l edgv.hid_dique_p edgv.hid_fonte_dagua_p edgv.hid_foz_maritima_l edgv.hid_foz_maritima_p edgv.hid_ilha_a edgv.hid_ilha_p edgv.hid_massa_dagua_a edgv.hid_quebramar_molhe_a edgv.hid_quebramar_molhe_l edgv.hid_queda_dagua_l edgv.hid_queda_dagua_p edgv.hid_recife_a edgv.hid_recife_p edgv.hid_rocha_em_agua_a edgv.hid_rocha_em_agua_p edgv.hid_sumidouro_vertedouro_p edgv.hid_terreno_sujeito_inundacao_a edgv.hid_trecho_drenagem_l edgv.hid_vala_a edgv.hid_vala_l edgv.laz_arquibancada_a edgv.laz_campo_quadra_a edgv.laz_campo_quadra_p edgv.laz_piscina_a edgv.laz_pista_competicao_a edgv.laz_pista_competicao_l edgv.laz_pista_competicao_p edgv.laz_ruina_a edgv.laz_ruina_p edgv.laz_sitio_arqueologico_a edgv.laz_sitio_arqueologico_p edgv.lml_area_densamente_edificada_a edgv.lml_area_pub_militar_a edgv.lml_area_urbana_isolada_a edgv.lml_distrito_a edgv.lml_municipio_a edgv.lml_nome_local_p edgv.lml_pais_a edgv.lml_posic_geo_localidade_p edgv.lml_terra_indigena_a edgv.lml_terra_publica_a edgv.lml_unidade_conservacao_a edgv.lml_unidade_federacao_a edgv.lml_unidade_protecao_integral_a edgv.lml_unidade_uso_sustentavel_a edgv.pto_marco_de_limite_p edgv.pto_pto_est_med_fenomenos_p edgv.pto_pto_geod_topo_controle_p edgv.pto_pto_ref_geod_topo_p edgv.rel_alteracao_fisiografica_antropica_a edgv.rel_alteracao_fisiografica_antropica_l edgv.rel_alteracao_fisiografica_antropica_p edgv.rel_aterro_a edgv.rel_aterro_l edgv.rel_aterro_p edgv.rel_corte_a edgv.rel_corte_l edgv.rel_corte_p edgv.rel_curva_batimetrica_l edgv.rel_curva_nivel_l edgv.rel_dolina_a edgv.rel_dolina_p edgv.rel_duna_a edgv.rel_duna_l edgv.rel_duna_p edgv.rel_elemento_fisiografico_natural_a edgv.rel_elemento_fisiografico_natural_l edgv.rel_elemento_fisiografico_natural_p edgv.rel_gruta_caverna_l edgv.rel_gruta_caverna_p edgv.rel_pico_p edgv.rel_ponto_cotado_altimetrico_p edgv.rel_ponto_cotado_batimetrico_p edgv.rel_rocha_a edgv.rel_rocha_l edgv.rel_rocha_p edgv.rel_terreno_exposto_a edgv.rod_trecho_rodoviario_a edgv.rod_trecho_rodoviario_l edgv.snb_barragem_calcadao_a edgv.snb_dep_abast_agua_a edgv.snb_dep_abast_agua_p edgv.tra_caminho_aereo_l edgv.tra_caminho_carrocavel_l edgv.tra_entroncamento_pto_p edgv.tra_funicular_l edgv.tra_passagem_elevada_viaduto_a edgv.tra_passagem_elevada_viaduto_l edgv.tra_passagem_elevada_viaduto_p edgv.tra_passagem_nivel_p edgv.tra_patio_a edgv.tra_ponte_a edgv.tra_ponte_l edgv.tra_ponte_p edgv.tra_travessia_l edgv.tra_travessia_p edgv.tra_travessia_pedestre_a edgv.tra_travessia_pedestre_l edgv.tra_travessia_pedestre_p edgv.tra_trilha_picada_l edgv.tra_tunel_a edgv.tra_tunel_l edgv.tra_tunel_p edgv.veg_brejo_pantano_a edgv.veg_caatinga_a edgv.veg_campinarana_a edgv.veg_campo_a edgv.veg_cerrado_a edgv.veg_floresta_a edgv.veg_mangue_a edgv.veg_reflorestamento_a edgv.veg_veg_area_contato_a edgv.veg_veg_cultivada_a edgv.veg_veg_restinga_a edgv.ver_arvore_isolada_p edgv.ver_jardim_a edgv.aux_obstaculo_vertical_p edgv.enc_subest_transm_distrib_energia_eletrica_p
- DestDataset_POSTGIS = gothic_25k_4674_edgv30   # Database
- FEATURE_TYPES_3 = cb.adm_area_pub_civil_a cb.adm_area_pub_militar_a cb.adm_edif_pub_civil_a cb.adm_edif_pub_civil_p cb.adm_edif_pub_militar_a cb.adm_edif_pub_militar_p cb.adm_posto_fiscal_a cb.adm_posto_fiscal_p cb.adm_posto_pol_rod_a cb.adm_posto_pol_rod_p cb.asb_area_abast_agua_a cb.asb_area_saneamento_a cb.asb_cemiterio_a cb.asb_cemiterio_p cb.asb_dep_abast_agua_a cb.asb_dep_abast_agua_p cb.asb_dep_saneamento_a cb.asb_dep_saneamento_p cb.asb_edif_abast_agua_a cb.asb_edif_abast_agua_p cb.asb_edif_saneamento_a cb.asb_edif_saneamento_p cb.eco_area_agrop_ext_veg_pesca_a cb.eco_area_comerc_serv_a cb.eco_area_ext_mineral_a cb.eco_area_industrial_a cb.eco_deposito_geral_a cb.eco_deposito_geral_p cb.eco_edif_agrop_ext_veg_pesca_a cb.eco_edif_agrop_ext_veg_pesca_p cb.eco_edif_comerc_serv_a cb.eco_edif_comerc_serv_p cb.eco_edif_ext_mineral_a cb.eco_edif_ext_mineral_p cb.eco_edif_industrial_a cb.eco_edif_industrial_p cb.eco_equip_agropec_a cb.eco_equip_agropec_l cb.eco_equip_agropec_p cb.eco_ext_mineral_a cb.eco_ext_mineral_p cb.eco_plataforma_a cb.eco_plataforma_p cb.edu_area_ensino_a cb.edu_area_lazer_a cb.edu_area_religiosa_a cb.edu_area_ruinas_a cb.edu_arquibancada_a cb.edu_arquibancada_p cb.edu_campo_quadra_a cb.edu_campo_quadra_p cb.edu_coreto_tribuna_a cb.edu_coreto_tribuna_p cb.edu_edif_const_lazer_a cb.edu_edif_const_lazer_p cb.edu_edif_const_turistica_a cb.edu_edif_const_turistica_p cb.edu_edif_ensino_a cb.edu_edif_ensino_p cb.edu_edif_religiosa_a cb.edu_edif_religiosa_p cb.edu_piscina_a cb.edu_pista_competicao_l cb.edu_ruina_a cb.edu_ruina_p cb.enc_antena_comunic_p cb.enc_area_comunicacao_a cb.enc_area_energia_eletrica_a cb.enc_edif_comunic_a cb.enc_edif_comunic_p cb.enc_edif_energia_a cb.enc_edif_energia_p cb.enc_est_gerad_energia_eletr_a cb.enc_est_gerad_energia_eletr_l cb.enc_est_gerad_energia_eletr_p cb.enc_grupo_transformadores_a cb.enc_grupo_transformadores_p cb.enc_hidreletrica_a cb.enc_hidreletrica_l cb.enc_hidreletrica_p cb.enc_termeletrica_a cb.enc_termeletrica_p cb.enc_torre_comunic_p cb.enc_torre_energia_p cb.enc_trecho_comunic_l cb.enc_trecho_energia_l cb.enc_zona_linhas_energia_com_a cb.hid_area_umida_a cb.hid_bacia_hidrografica_a cb.hid_banco_areia_a cb.hid_banco_areia_l cb.hid_barragem_a cb.hid_barragem_l cb.hid_barragem_p cb.hid_comporta_l cb.hid_comporta_p cb.hid_corredeira_a cb.hid_corredeira_l cb.hid_corredeira_p cb.hid_fonte_dagua_p cb.hid_foz_maritima_a cb.hid_foz_maritima_l cb.hid_foz_maritima_p cb.hid_ilha_a cb.hid_ilha_l cb.hid_ilha_p cb.hid_massa_dagua_a cb.hid_natureza_fundo_a cb.hid_natureza_fundo_l cb.hid_natureza_fundo_p cb.hid_quebramar_molhe_a cb.hid_quebramar_molhe_l cb.hid_queda_dagua_a cb.hid_queda_dagua_l cb.hid_queda_dagua_p cb.hid_recife_a cb.hid_recife_l cb.hid_recife_p cb.hid_reservatorio_hidrico_a cb.hid_rocha_em_agua_a cb.hid_rocha_em_agua_p cb.hid_sumidouro_vertedouro_p cb.hid_terreno_suj_inundacao_a cb.hid_trecho_drenagem_l cb.hid_trecho_massa_dagua_a cb.lim_area_de_litigio_a cb.lim_area_de_propriedade_particular_a cb.lim_area_desenv_controle_a cb.lim_area_desenv_controle_p cb.lim_area_uso_comunitario_a cb.lim_area_uso_comunitario_p cb.lim_bairro_a cb.lim_delimitacao_fisica_l cb.lim_distrito_a cb.lim_limite_intra_munic_adm_l cb.lim_limite_operacional_l cb.lim_limite_particular_l cb.lim_limite_politico_adm_l cb.lim_linha_de_limite_l cb.lim_marco_de_limite_p cb.lim_municipio_a cb.lim_outras_unid_protegidas_a cb.lim_outras_unid_protegidas_p cb.lim_outros_limites_oficiais_l cb.lim_pais_a cb.lim_regiao_administrativa_a cb.lim_sub_distrito_a cb.lim_terra_indigena_a cb.lim_terra_indigena_p cb.lim_terra_publica_a cb.lim_terra_publica_p cb.lim_unidade_conserv_nao_snuc_a cb.lim_unidade_conserv_nao_snuc_p cb.lim_unidade_federacao_a cb.lim_unidade_protecao_integral_a cb.lim_unidade_protecao_integral_p cb.lim_unidade_uso_sustentavel_a cb.lim_unidade_uso_sustentavel_p cb.loc_aglom_rural_de_ext_urbana_p cb.loc_aglomerado_rural_isolado_p cb.loc_area_edificada_a cb.loc_area_habitacional_a cb.loc_area_urbana_isolada_a cb.loc_capital_p cb.loc_cidade_p cb.loc_edif_habitacional_a cb.loc_edif_habitacional_p cb.loc_edificacao_a cb.loc_edificacao_p cb.loc_hab_indigena_a cb.loc_hab_indigena_p cb.loc_nome_local_p cb.loc_vila_p cb.pto_area_est_med_fenom_a cb.pto_edif_constr_est_med_fen_a cb.pto_edif_constr_est_med_fen_p cb.pto_pto_controle_p cb.pto_pto_est_med_fenomenos_p cb.pto_pto_ref_geod_topo_p cb.rel_alter_fisiog_antropica_a cb.rel_alter_fisiog_antropica_l cb.rel_curva_batimetrica_l cb.rel_curva_nivel_l cb.rel_dolina_a cb.rel_dolina_p cb.rel_duna_a cb.rel_duna_p cb.rel_elemento_fisiog_natural_a cb.rel_elemento_fisiog_natural_l cb.rel_elemento_fisiog_natural_p cb.rel_gruta_caverna_p cb.rel_pico_p cb.rel_ponto_cotado_altimetrico_p cb.rel_ponto_cotado_batimetrico_p cb.rel_rocha_a cb.rel_rocha_p cb.rel_terreno_exposto_a cb.sau_area_saude_a cb.sau_area_servico_social_a cb.sau_edif_saude_a cb.sau_edif_saude_p cb.sau_edif_servico_social_a cb.sau_edif_servico_social_p cb.tra_area_duto_a cb.tra_area_estrut_transporte_a cb.tra_arruamento_l cb.tra_atracadouro_a cb.tra_atracadouro_l cb.tra_atracadouro_p cb.tra_caminho_aereo_l cb.tra_ciclovia_l cb.tra_condutor_hidrico_l cb.tra_cremalheira_l cb.tra_cremalheira_p cb.tra_eclusa_a cb.tra_eclusa_l cb.tra_eclusa_p cb.tra_edif_constr_aeroportuaria_a cb.tra_edif_constr_aeroportuaria_p cb.tra_edif_constr_portuaria_a cb.tra_edif_constr_portuaria_p cb.tra_edif_metro_ferroviaria_a cb.tra_edif_metro_ferroviaria_p cb.tra_edif_rodoviaria_a cb.tra_edif_rodoviaria_p cb.tra_entroncamento_p cb.tra_faixa_seguranca_a cb.tra_fundeadouro_a cb.tra_fundeadouro_l cb.tra_fundeadouro_p cb.tra_funicular_l cb.tra_funicular_p cb.tra_galeria_bueiro_l cb.tra_galeria_bueiro_p cb.tra_girador_ferroviario_p cb.tra_local_critico_a cb.tra_local_critico_l cb.tra_local_critico_p cb.tra_obstaculo_navegacao_a cb.tra_obstaculo_navegacao_l cb.tra_obstaculo_navegacao_p cb.tra_passag_elevada_viaduto_l cb.tra_passag_elevada_viaduto_p cb.tra_passagem_nivel_p cb.tra_patio_a cb.tra_patio_p cb.tra_pista_ponto_pouso_a cb.tra_pista_ponto_pouso_l cb.tra_pista_ponto_pouso_p cb.tra_ponte_l cb.tra_ponte_p cb.tra_posto_combustivel_a cb.tra_posto_combustivel_p cb.tra_sinalizacao_p cb.tra_travessia_l cb.tra_travessia_p cb.tra_travessia_pedestre_l cb.tra_travessia_pedestre_p cb.tra_trecho_duto_l cb.tra_trecho_ferroviario_l cb.tra_trecho_hidroviario_l cb.tra_trecho_rodoviario_l cb.tra_trilha_picada_l cb.tra_tunel_l cb.tra_tunel_p cb.veg_brejo_pantano_a cb.veg_caatinga_a cb.veg_campinarana_a cb.veg_campo_a cb.veg_cerrado_cerradao_a cb.veg_estepe_a cb.veg_floresta_a cb.veg_macega_chavascal_a cb.veg_mangue_a cb.veg_veg_area_contato_a cb.veg_veg_cultivada_a cb.veg_veg_restinga_a cb.tra_identific_trecho_rod_p

Readers:
- POSTGIS_1: POSTGIS from $(SourceDataset_POSTGIS_4)
- POSTGIS_2: POSTGIS from $(SourceDataset_POSTGIS_3)

Writers:
- POSTGIS_3: POSTGIS to $(DestDataset_POSTGIS)

Note: Banco Resource para definir as camadas de saída
aer_pista_ponto_pouso_a (reader POSTGIS_2)
    attributes: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
Note: Banco EDGV 2.1.3
adm_area_pub_civil_a (reader POSTGIS_1)
    attributes: id serial, geometriaaproximada int2, administracao int2, altitudeortometrica float4, altura float4, alturaestimada float4, alturalamina float4, alturamediaindividuos float4, alturamediamargem float4, anocriacao varchar(255), anodereferencia int4, antropizada int2, areaoficial varchar(255), areaoficialha float4, arranjofases varchar(255), atividade int2, atolegal varchar(255), bitola int2, calado float4, caladomax float4, caladomaxseca float4, canteirodivisorio int2, capaccarga float4, caracteristicafloresta int2, cargasuportmaxima float4, causa int2, causaexposicao int2, chamine int2, classe varchar(255), classificacao varchar(255),
      classificacaoporte int2, codestacao varchar(255), codigoestacao varchar(255), codigohidreletrica varchar(255), codigootto int4, codiso3166 varchar(255), codponto varchar(255), codprojeto varchar(255), codtrechoferrov varchar(255), codtrechorodov varchar(255), coincidecomdentrode int2, coletiva int2, combrenovavel int2, compartilhado int2, concessionaria varchar(255), construcao int2, cota int4, cotacomprovada int2, cultivopredominante int2, datasituacaojuridica date, datavisita varchar(255), denominacaoassociada int2, denso int2, dentrodepoligono int2, depressao int2, descricao varchar(255), desnivel float4, destenergelet int2, destinacaofundeadouro int2, destinadoa int2,
      eixoprincipal int2, eletrificada int2, emarruamento int2, emduto int2, ensino int2, escala varchar(255), espacamentoindividuos float4, especie int2, especiepredominante int2, espessalgas int2, espessuradap float4, extensao float4, extensaotrecho float4, finalidade int2, fixa int2, formaextracao int2, funcaoedifmetroferrov int2, gabhorizsup float4, gabvertsup float4, geocodigo varchar(255), geracao int2, grupoetnico varchar(255), historicomodificacao varchar(255), homologacao int2, identificador varchar(255), indice int2, inom varchar(255), isolada int2, jurisdicao int2, largura float4,
      larguramedia float4, latitude varchar(255), longitude varchar(255), matconstr int2, materializado int2, materialpredominante int2, mattransp int2, mi varchar(255), modalidade int2, modaluso int2, motivodescontinuidade int2, multimodal int2, namaximomaximorum int4, namaximooperacional int4, nascente int2, navegabilidade int2, nivelatencao int2, nivelotto int4, nome varchar(255), nomeabrev varchar(255), nometi varchar(255), nrdutos int4, nrfaixas int4, nrlinhas int2, nrpistas int4, numcircuitos int4, obs varchar(255), obssituacao varchar(255), ocorrenciaem int2, operacional int2,
      orgaoenteresp varchar(255), orgresp varchar(255), outrarefalt varchar(255), outrarefplan varchar(255), ovgd int2, perimetrooficial float4, periodicidadeinunda varchar(255), pesosuportmaximo float4, posicaopista int2, posicaorelativa int2, posicaoreledific int2, potenciafiscalizada float4, potenciaoutorgada float4, procextracao int2, profundidade int4, profundidademedia float4, proximidade int2, qualidagua int2, rede int2, referencialaltim int2, referencialgrav int2, regime int2, relacionado int2, religiao varchar(255), residuo int2, revestimento int2, salinidade int2, setor int2, sigla varchar(255), sistemageodesico int2,
      situacaoagua int2, situacaocosta int2, situacaoemagua int2, situacaoespacial int2, situacaofisica int2, situacaojuridica int2, situacaomarco int2, situamare int2, tensaoeletrica float4, terreno int2, tipoaglomrurisol int2, tipoalterantrop int2, tipoareaumida int2, tipoareausocomun int2, tipoassociado int2, tipoatracad int2, tipobanco int2, tipobrejopantano int2, tipocaminhoaereo int2, tipocampo int2, tipocampoquadra int2, tipocapital int2, tipocemiterio int2, tipocerr int2, tipoclassecnae int2, tipocombustivel int2, tipocondutor int2, tipoconteudo int2, tipodelimfis int2, tipodepabast int2,
      tipodepgeral int2, tipodepsaneam int2, tipodivisaocnae int2, tipoedifabast int2, tipoedifaero int2, tipoedifagropec int2, tipoedifcivil int2, tipoedifcomercserv int2, tipoedifcomunic int2, tipoedifenergia int2, tipoediflazer int2, tipoedifmil int2, tipoedifport int2, tipoedifrelig int2, tipoedifrod int2, tipoedifsaneam int2, tipoedifturist int2, tipoelemnat int2, tipoentroncamento int2, tipoequipagropec int2, tipoestgerad int2, tipoexposicao int2, tipoextmin int2, tipofontedagua int2, tipogrutacaverna int2, tipoilha int2, tipolavoura int2, tipolimareaesp int2, tipolimintramun int2, tipolimmassa int2,
      tipolimoper int2, tipolimpol int2, tipolocalcrit int2, tipomacchav int2, tipomaqtermica int2, tipomarcolim int2, tipomassadagua int2, tipoobst int2, tipooutlimofic int2, tipooutunidprot int2, tipopassagviad int2, tipopista int2, tipoplataforma int2, tipopocomina int2, tipoponte int2, tipopostofisc int2, tipopostopol int2, tipoprodutoresiduo int2, tipoptocontrole int2, tipoptoenergia int2, tipoptoestmed int2, tipoptorefgeodtopo int2, tipoquebramolhe int2, tipoqueda int2, tiporecife int2, tiporef int2, tiporesiduo int2, tiporocha int2, tiposecaocnae int2, tiposinal int2,
      tiposumvert int2, tipoterrexp int2, tipotorre int2, tipotravessia int2, tipotravessiaped int2, tipotrechocomunic int2, tipotrechoduto int2, tipotrechoferrov int2, tipotrechomassa int2, tipotrechorod int2, tipotunel int2, tipounidprotinteg int2, tipounidusosust int2, tipousocaminhoaer int2, tipousoedif int2, trafego int2, tratamento int2, unidadevolume int2, usopista int2, usoprincipal int2, valorvolume float4, vaolivrehoriz float4, vaovertical float4, velocidademedcorrente float4, volumeutil int4
    -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryValidator
GeometryValidator
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme CONSECUTIVE_IDENTICAL_VERTICES_2D CHECK_Z]YES]FME_CONTROLLER_QUERY_FILE]transformers/dependencies/geometryvalidator8/CONSECUTIVE_IDENTICAL_VERTICES_2D.fme MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme NULL_REMOVAL FME_CONTROLLER_QUERY_FILE]transformers/dependencies/geometryvalidator8/NULL_REMOVAL.fme]FME_CONTROLLER_CHOICE]NULL_REMOVAL OGC_SIMPLE_CHECK LEGACY_OGC]No]FME_CONTROLLER_QUERY_FILE]transformers/dependencies/geometryvalidator8/OGC_SIMPLE_CHECK.fme OGC_VALID_CHECK OGC_VERSION]V1.2.0]FME_CONTROLLER_QUERY_FILE]transformers/dependencies/geometryvalidator8/OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers/dependencies/geometryvalidator8/PLANAR_SURFACE.fme SELF_INTERSECTING CHECK_HOLE_TOUCHING_POLYGON]No]CONNECT_Z_MODE_SI]FIRST_WINS]SELF_INTERSECTION_TOLERANCE]None]FME_CONTROLLER_QUERY_FILE]transformers/dependencies/geometryvalidator8/SELF_INTERSECTING.fme SHELL_VALIDATION FLIP_APPEARANCE_MODE]FLIP_APPEARANCES]FME_CONTROLLER_QUERY_FILE]transformers/dependencies/geometryvalidator8/SHELL_VALIDATION.fme SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]0.0]FME_CONTROLLER_QUERY_FILE]transformers/dependencies/geometryvalidator8/TYPE_REPAIR.fme MISMATCHED_DIMENSIONS FORCE_DIMENSION]2D]FME_CONTROLLER_QUERY_FILE]transformers/dependencies/geometryvalidator8/MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers/dependencies/geometryvalidator8/MISSING_MEASURES_AND_ELEVATIONS.fme SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> Deaggregator_3
    FAILED -> Deaggregator_3
    REPAIRED -> Deaggregator_3
Deaggregator_3
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryFilter
GeometryFilter
    FILTER_MODE = SIMPLE
    FILTER_MULTI = FILTER_TYPES]"Point Line Area"]FME_CONTROLLER_QUERY_FILE]]FME_CONTROLLER_CHOICE]Simple
    Point -> Tester_2
    Curve -> Tester_3
    Area -> Tester_5
Tester_2
    BOOL_OP = OR
    TEST_CLAUSE = CASE_INSENSITIVE_TEST @Value(fme_feature_type) ENDS_WITH _p
    TEST_MODE = TEST
    PASSED -> NullAttributeMapper
Tester_3
    BOOL_OP = OR
    TEST_CLAUSE = CASE_INSENSITIVE_TEST @Value(fme_feature_type) ENDS_WITH _l
    TEST_MODE = CASE_INSENSITIVE_TEST
    PASSED -> NullAttributeMapper
Tester_5
    BOOL_OP = OR
    TEST_CLAUSE = CASE_INSENSITIVE_TEST @Value(fme_feature_type) ENDS_WITH _a
    TEST_MODE = CASE_INSENSITIVE_TEST
    PASSED -> NullAttributeMapper
Note: Maps 999 to 9999
NullAttributeMapper
    ATTRCHOICE = Selected Attributes
    ATTRLIST = administracao altitudeortometrica altura alturaestimada alturalamina alturamediaindividuos alturamediamargem anocriacao anodereferencia antropizada areaoficial areaoficialha arranjofases atividade atolegal bitola calado caladomax caladomaxseca canteirodivisorio capaccarga caracteristicafloresta cargasuportmaxima causa causaexposicao chamine classe classificacao classificacaoporte codestacao codigoestacao codigohidreletrica codigootto codiso3166 codponto codprojeto codtrechoferrov codtrechorodov coincidecomdentrode coletiva combrenovavel compartilhado concessionaria construcao cota cotacomprovada cultivopredominante datasituacaojuridica datavisita denominacaoassociada denso dentrodepoligono depressao descricao desnivel destenergelet destinacaofundeadouro destinadoa eixoprincipal eletrificada emarruamento emduto ensino escala espacamentoindividuos especie especiepredominante espessalgas espessuradap extensao extensaotrecho finalidade fixa fme_feature_type formaextracao funcaoedifmetroferrov gabhorizsup gabvertsup geocodigo geometriaaproximada geracao grupoetnico historicomodificacao homologacao id identificador indice inom isolada jurisdicao largura larguramedia latitude longitude matconstr materializado materialpredominante mattransp mi modalidade modaluso motivodescontinuidade multimodal namaximomaximorum namaximooperacional nascente navegabilidade nivelatencao nivelotto nome nomeabrev nometi nrdutos nrfaixas nrlinhas nrpistas numcircuitos obs obssituacao ocorrenciaem operacional orgaoenteresp orgresp outrarefalt outrarefplan ovgd perimetrooficial periodicidadeinunda pesosuportmaximo posicaopista posicaorelativa posicaoreledific potenciafiscalizada potenciaoutorgada procextracao profundidade profundidademedia proximidade qualidagua rede referencialaltim referencialgrav regime relacionado religiao residuo revestimento salinidade setor sigla sistemageodesico situacaoagua situacaocosta situacaoemagua situacaoespacial situacaofisica situacaojuridica situacaomarco situamare tensaoeletrica terreno tipoaglomrurisol tipoalterantrop tipoareaumida tipoareausocomun tipoassociado tipoatracad tipobanco tipobrejopantano tipocaminhoaereo tipocampo tipocampoquadra tipocapital tipocemiterio tipocerr tipoclassecnae tipocombustivel tipocondutor tipoconteudo tipodelimfis tipodepabast tipodepgeral tipodepsaneam tipodivisaocnae tipoedifabast tipoedifaero tipoedifagropec tipoedifcivil tipoedifcomercserv tipoedifcomunic tipoedifenergia tipoediflazer tipoedifmil tipoedifport tipoedifrelig tipoedifrod tipoedifsaneam tipoedifturist tipoelemnat tipoentroncamento tipoequipagropec tipoestgerad tipoexposicao tipoextmin tipofontedagua tipogrutacaverna tipoilha tipolavoura tipolimareaesp tipolimintramun tipolimmassa tipolimoper tipolimpol tipolocalcrit tipomacchav tipomaqtermica tipomarcolim tipomassadagua tipoobst tipooutlimofic tipooutunidprot tipopassagviad tipopista tipoplataforma tipopocomina tipoponte tipopostofisc tipopostopol tipoprodutoresiduo tipoptocontrole tipoptoenergia tipoptoestmed tipoptorefgeodtopo tipoquebramolhe tipoqueda tiporecife tiporef tiporesiduo tiporocha tiposecaocnae tiposinal tiposumvert tipoterrexp tipotorre tipotravessia tipotravessiaped tipotrechocomunic tipotrechoduto tipotrechoferrov tipotrechomassa tipotrechorod tipotunel tipounidprotinteg tipounidusosust tipousocaminhoaer tipousoedif trafego tratamento unidadevolume usopista usoprincipal valorvolume vaolivrehoriz vaovertical velocidademedcorrente volumeutil
    NEW_VALUE = 9999
    NULL_TREATMENT = New Value
    OTHER_VALUE = 999
    -> PythonCaller_EDGV3
Note: mapeamento
PythonCaller_EDGV3
    NEW_ATTRIBUTES = CLASS_NOT_FOUND
    PYTHONSOURCE:
      import fme
      import fmeobjects
      import copy
      import sys
      import os
      import json

      class FeatureProcessor(object):
          def __init__(self):
              self.mappingDict = self.buildFileDict(FME_MacroValues['JsonMapeamento'])
              self.mappingType = FME_MacroValues['direcao']

          def buildFileDict(self, mappingPath):
              with open(mappingPath, 'r', encoding='utf-8') as file:
                  mapDict = json.loads(file.read())
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          if feature.getAttribute(attr) == 'f':
                              featDict[attr] = 'False'
                          elif feature.getAttribute(attr) == 't':
                              featDict[attr] = 'True'
                          else:
                              featDict[attr] = feature.getAttribute(attr)
                      else:
                          featDict[attr] = None
              if feature.performFunction('@GeometryType()') == 'fme_polygon' or feature.performFunction('@GeometryType()') == 'fme_donut':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              else:
                   featDict["INVALID_GEOM"] = True
              return featDict

          def evaluateExpression(self, featDict, expression):
              if not expression["nome_atributo"] in featDict:
                  return False
              if expression["valor"] is None or expression["valor"] == "":
                  return featDict[expression["nome_atributo"]] is None or featDict[expression["nome_atributo"]] == ""
              else:
                  return u"{0}".format(featDict[expression["nome_atributo"]]) == u"{0}".format(expression["valor"])

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "ida":
                  key_attr_origin = "attr_ida"
                  key_attr_destiny = "attr_volta"
                  key_value_origin = "valor_ida"
                  key_value_destiny = "valor_volta"
                  key_default = "atributos_default_ida"
                  key_filter = "filtro_ida"
                  key_class_origin = "classe_ida"
                  key_class_destiny = "classe_volta"
                  key_group_origin = "tupla_ida"
                  key_group_destiny = "tupla_volta"
                  key_affix_origin = "afixo_geom_ida"
                  key_affix_destiny = "afixo_geom_volta"
                  key_schema_origin = "schema_ida"
                  key_schema_destiny = "schema_volta"
                  key_class_affix_origin = "com_afixo_geom_ida"
                  key_class_affix_destiny = "com_afixo_geom_volta"
                  key_class_schema_origin = "com_schema_ida"
                  key_class_schema_destiny = "com_schema_volta"
                  key_agregar = "agregar_geom_ida"
              else:
                  key_attr_origin = "attr_volta"
                  key_attr_destiny = "attr_ida"
                  key_value_origin = "valor_volta"
                  key_value_destiny = "valor_ida"
                  key_default = "atributos_default_volta"
                  key_filter = "filtro_volta"
                  key_class_origin = "classe_volta"
                  key_class_destiny = "classe_ida"
                  key_group_origin = "tupla_volta"
                  key_group_destiny = "tupla_ida"
                  key_affix_origin = "afixo_geom_volta"
                  key_affix_destiny = "afixo_geom_ida"
                  key_schema_origin = "schema_volta"
                  key_schema_destiny = "schema_ida"
                  key_class_affix_origin = "com_afixo_geom_volta"
                  key_class_affix_destiny = "com_afixo_geom_ida"
                  key_class_schema_origin = "com_schema_volta"
                  key_class_schema_destiny = "com_schema_ida"
                  key_agregar = "agregar_geom_volta"

              featDict["fme_feature_type_original"] = featDict["fme_feature_type"]

              if key_schema_origin in self.mappingDict and self.mappingDict[key_schema_origin]:
                  featDict["fme_feature_type"] = featDict["fme_feature_type"][len(self.mappingDict[key_schema_origin])+1:]

              featDict["fme_feature_type_sem_schema"] = featDict["fme_feature_type"]

              if key_affix_origin in self.mappingDict and 'tipo' in self.mappingDict[key_affix_origin] and self.mappingDict[key_affix_origin]['tipo'] == 'sufixo':
                  featDict["fme_feature_type"] = featDict["fme_feature_type"][:-len(self.mappingDict[key_affix_origin][featDict["$GEOM_TYPE"]])]
                  featDict["fme_feature_type_sem_afixo"] = featDict["fme_feature_type_original"][:-len(self.mappingDict[key_affix_origin][featDict["$GEOM_TYPE"]])]

              if key_affix_origin in self.mappingDict and 'tipo' in self.mappingDict[key_affix_origin] and self.mappingDict[key_affix_origin]['tipo'] == 'prefixo':
                  featDict["fme_feature_type"] = featDict["fme_feature_type"][len(self.mappingDict[key_affix_origin][featDict["$GEOM_TYPE"]]):]
                  featDict["fme_feature_type_sem_afixo"] = featDict["fme_feature_type_original"][len(self.mappingDict[key_affix_origin][featDict["$GEOM_TYPE"]]):]

              should_map = False
              for classmap in self.mappingDict['mapeamento_classes']:
                  if "sentido" not in classmap or ("sentido" in classmap and classmap["sentido"] == self.mappingType):
                      if key_class_affix_origin in classmap and classmap[key_class_affix_origin] and key_class_schema_origin in classmap and classmap[key_class_schema_origin]:
                          class_name = featDict["fme_feature_type_original"]
                      elif key_class_affix_origin in classmap and classmap[key_class_affix_origin]:
                          class_name = featDict["fme_feature_type_sem_schema"]
                      elif key_class_schema_origin in classmap and classmap[key_class_schema_origin]:
                          class_name = featDict["fme_feature_type_sem_afixo"]
                      else:
                           class_name = featDict["fme_feature_type"]

                      if classmap[key_class_origin] == class_name:
                          if key_filter in classmap:
                              if not self.evaluateFilter(featDict, classmap[key_filter]):
                                  continue
                          should_map = True
              if not should_map:
                  featDict["CLASS_NOT_FOUND"] = True
                  return featDict

              mappedFeat = copy.deepcopy(featDict)

              if key_default in self.mappingDict:
                  for default in self.mappingDict[key_default]:
                      mappedFeat[default["nome_atributo"]] = default["valor"]

              if 'mapeamento_atributos' in self.mappingDict:
                  for attmap in self.mappingDict['mapeamento_atributos']:
                      if attmap[key_attr_origin] in mappedFeat:
                          mappedFeat[attmap[key_attr_destiny]] = featDict[attmap[key_attr_origin]]
                          if "traducao" in attmap:
                              for valuemap in attmap["traducao"]:
                                  if u"{0}".format(valuemap[key_value_origin]) == u"{0}".format(featDict[attmap[key_attr_origin]]) and ("sentido" not in valuemap or ("sentido" in valuemap and valuemap["sentido"] == self.mappingType)):
                                      mappedFeat[attmap[key_attr_destiny]] = valuemap[key_value_destiny]

              if "mapeamento_multiplo" in self.mappingDict:
                  for attmap in self.mappingDict['mapeamento_multiplo']:
                      if "sentido" not in attmap or ("sentido" in attmap and attmap["sentido"] == self.mappingType):
                          if all([self.evaluateExpression(featDict, condition) for condition in attmap[key_group_origin]]):
                              for valuemap in attmap[key_group_destiny]:
                                  if "concatenar" in valuemap and valuemap["concatenar"] and valuemap["nome_atributo"] in mappedFeat and mappedFeat[valuemap["nome_atributo"]]:
                                      mappedFeat[valuemap["nome_atributo"]] = mappedFeat[valuemap["nome_atributo"]] + ' | ' + valuemap["valor"]
                                  else:
                                      mappedFeat[valuemap["nome_atributo"]] = valuemap["valor"]

              if 'mapeamento_classes' in self.mappingDict:
                  for classmap in self.mappingDict['mapeamento_classes']:
                      if "sentido" not in classmap or ("sentido" in classmap and classmap["sentido"] == self.mappingType):
                          if key_class_affix_origin in classmap and classmap[key_class_affix_origin] and key_class_schema_origin in classmap and classmap[key_class_schema_origin]:
                              class_name = featDict["fme_feature_type_original"]
                          elif key_class_affix_origin in classmap and classmap[key_class_affix_origin]:
                              class_name = featDict["fme_feature_type_sem_schema"]
                          elif key_class_schema_origin in classmap and classmap[key_class_schema_origin]:
                              class_name = featDict["fme_feature_type_sem_afixo"]
                          else:
                              class_name = featDict["fme_feature_type"]

                          if classmap[key_class_origin] == class_name:
                              if key_filter in classmap:
                                  if not self.evaluateFilter(featDict, classmap[key_filter]):
                                      continue

                              mappedFeat["fme_feature_type"] = classmap[key_class_destiny]

                              if key_class_affix_destiny in classmap and classmap[key_class_affix_destiny]:
                                  pass
                              elif key_affix_destiny in self.mappingDict and 'tipo' in self.mappingDict[key_affix_destiny]:
                                  if self.mappingDict[key_affix_destiny]['tipo'] == 'sufixo':
                                      mappedFeat["fme_feature_type"] = mappedFeat["fme_feature_type"] + self.mappingDict[key_affix_destiny][featDict["$GEOM_TYPE"]]

                                  if self.mappingDict[key_affix_destiny]['tipo'] == 'prefixo':
                                      mappedFeat["fme_feature_type"] = self.mappingDict[key_affix_destiny][featDict["$GEOM_TYPE"]] + mappedFeat["fme_feature_type"]

                              if key_class_schema_destiny in classmap and classmap[key_class_schema_destiny]:
                                  pass
                              elif key_schema_destiny in self.mappingDict and self.mappingDict[key_schema_destiny]:
                                  mappedFeat["fme_feature_type"] = self.mappingDict[key_schema_destiny] + '.' + mappedFeat["fme_feature_type"]


                              if key_default in classmap:
                                  for default in classmap[key_default]:
                                      mappedFeat[default["nome_atributo"]] = default["valor"]

                              if "mapeamento_atributos" in classmap:
                                  for attmap in classmap['mapeamento_atributos']:
                                      if attmap[key_attr_origin] in featDict:
                                          if attmap[key_attr_destiny] not in mappedFeat:
                                              mappedFeat[attmap[key_attr_destiny]] = featDict[attmap[key_attr_origin]]
                                          if "traducao" in attmap:
                                              for valuemap in attmap["traducao"]:
                                                  if u"{0}".format(valuemap[key_value_origin]) == u"{0}".format(featDict[attmap[key_attr_origin]]) and ("sentido" not in valuemap or ("sentido" in valuemap and valuemap["sentido"] == self.mappingType)):
                                                      mappedFeat[attmap[key_attr_destiny]] = valuemap[key_value_destiny]

                              if "mapeamento_multiplo" in classmap:
                                  for attmap in classmap['mapeamento_multiplo']:
                                      if "sentido" not in attmap or ("sentido" in attmap and attmap["sentido"] == self.mappingType):
                                          if all([self.evaluateExpression(featDict, condition) for condition in attmap[key_group_origin]]):
                                              for valuemap in attmap[key_group_destiny]:
                                                  if "concatenar" in valuemap and valuemap["concatenar"] and valuemap["nome_atributo"] in mappedFeat and mappedFeat[valuemap["nome_atributo"]]:
                                                      mappedFeat[valuemap["nome_atributo"]] = mappedFeat[valuemap["nome_atributo"]] + ' | ' + valuemap["valor"]
                                                  else:
                                                      mappedFeat[valuemap["nome_atributo"]] = valuemap["valor"]

                              if key_agregar in classmap:
                                  mappedFeat["AGGREGATE_GEOM"] = classmap[key_agregar]
                              elif key_agregar in self.mappingDict:
                                  mappedFeat["AGGREGATE_GEOM"] = self.mappingDict[key_agregar]

                              break

              return mappedFeat

          def mapDictToFeature(self, feat, featDict):
              for attr, value in featDict.items():
                  if value or value == 0:
                      feat.setAttribute(attr, u'{0}'.format(value))
                  else:
                      feat.setAttributeNullWithType(attr,0)
              if "AGGREGATE_GEOM" in featDict and featDict["AGGREGATE_GEOM"]:
                  feat.buildAggregateFeat([feat])
              return feat

          def input(self,feature):
              if feature.performFunction('@GeometryType()') == 'fme_aggregate':
                  features = feature.splitAggregate(True)
              else:
                  features = [feature]
              for simple_feature in features:
                  feat = self.buildFeatureDict(simple_feature)
                  if "INVALID_GEOM" in feat and not feat["INVALID_GEOM"]:
                      simple_feature.setAttribute("INVALID_GEOM", u'True')
                      self.pyoutput(simple_feature)
                      continue

                  outputFeatDict = self.convertFeature(feat)
                  if "CLASS_NOT_FOUND" in outputFeatDict and not outputFeatDict["CLASS_NOT_FOUND"]:
                      simple_feature.setAttribute("CLASS_NOT_FOUND", u'True')
                      self.pyoutput(simple_feature)
                  else:
                      outputFeature = self.mapDictToFeature(simple_feature, outputFeatDict)
                      self.pyoutput(outputFeature)

          def close(self):
              pass
    PYTHONSYMBOL = FeatureProcessor
    -> Tester_4
Note: Teste de mapeamento
Tester_4
    BOOL_OP = OR
    TEST_CLAUSE = TEST @Value(CLASS_NOT_FOUND) = True
    TEST_MODE = TEST
    PASSED -> DuplicateFilter
    FAILED -> Reprojector
DuplicateFilter
    INPUT_ORDERED_CHOICE = No
    KEYATTR = fme_feature_type
    UNIQUE -> CLASS_NOT_FOUND
CLASS_NOT_FOUND: Inspector
Reprojector
    DEST = EPSG:4674
    INTERPOLATION_TYPE_NAME = Nearest Neighbor
    RASTER_CELL_SIZE = Preserve Cells
    RASTER_TOLERANCE = 0.0
    REPROJECTED -> Deaggregator_4
Deaggregator_4
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> UniqueIdentifierGenerator
UniqueIdentifierGenerator
    UUID_ATTR = id
    UUID_FORMAT = UUID_ONLY
    -> Tester
Note: Remove classes inexistentes
Tester
    BOOL_OP = AND
    TEST_CLAUSE:
      TEST @Value(fme_feature_type) != edgv.hid_ilha_l
      TEST @Value(fme_feature_type) != edgv.hid_queda_dagua_a
      TEST @Value(fme_feature_type) != edgv.tra_patio_p
      TEST @Value(fme_feature_type) != edgv.veg_campo_l
      TEST @Value(fme_feature_type) != edgv.veg_floresta_l
    TEST_MODE = TEST
    PASSED -> Aggregator
Aggregator
    ACCUM_ATTRS_NAME = Use Attributes From One Feature
    AGGREGATE_TYPE = Homogeneous Collection (If Possible)
    GROUP_BY = id
    MODE = Geometry - Assemble One Level
    SEP = ,
    AGGREGATE -> Table1 (writer POSTGIS_3)
Table1 (writer POSTGIS_3)
