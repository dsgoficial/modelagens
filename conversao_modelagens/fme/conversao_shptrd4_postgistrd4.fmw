FME workspace conversao_shptrd4_postgistrd4.fmw

Parameters:
- SourceDataset_SHAPEFILE = ""C:\Users\diniz.1CGEO\Downloads\W055S26\PGB230.shp" "C:\Users\diniz.1CGEO\Downloads\W055S26\PGB485.shp" "C:\Users\diniz.1CGEO\Downloads\W055S26\PZD040.shp" "C:\Users\diniz.1CGEO\Downloads\W055S26\AAC000.shp" "C:\Users\diniz.1CGEO\Downloads\W055S26\AAC030.shp" "C:\Users\diniz.1CGEO\Downloads\W055S26\AAD010.shp" "C:\Users\diniz.1CGEO\Downloads\W055S26\AAD030.shp" "C:\Users\diniz.1CGEO\Downloads\W055S26\AAJ010.shp" "C:\Users\diniz.1CGEO\Downloads\W055S26\AAJ110.shp" "C:\Users\diniz.1CGEO\Downloads\W055S26\AAK030.shp" "C:\Users\diniz.1CGEO\Downloads\W055S26\AAK040.shp" "C:\Users\diniz.1CGEO\Downloads\W055S26\AAK100.shp" "C:\Users\diniz.1CGEO\Downloads\W055S26\AAK120.shp" "C:\Users\diniz.1CGEO\Downloads\W055S26\AAK160.shp" "C:\Users\diniz.1CGEO\Downloads\W055S26\AAL010.shp" "C:\Users\diniz.1CGEO\Downloads\W055S26\AAL015.shp" "C:\Users\diniz.1CGEO\Downloads\W055S26\AAL020.shp" "C:\Users\diniz.1CGEO\Downloads\W055S26\AAL030.shp" "C:\Users\diniz.1CGEO\Downloads\W055S26\AAL170.shp" "C:\Users\diniz.1CGEO\Downloads\W055S26\AAM020.shp" "C:\Users\diniz.1CGEO\Downloads\W055S26\ABA030.shp" "C:\Users\diniz.1CGEO\Downloads\W055S26\ABH080.shp" "C:\Users\diniz.1CGEO\Downloads\W055S26\ABH120.shp" "C:\Users\diniz.1CGEO\Downloads\W055S26\ABH130.shp" "C:\Users\diniz.1CGEO\Downloads\W055S26\ABH140.shp" "C:\Users\diniz.1CGEO\Downloads\W055S26\ABH165.shp" "C:\Users\diniz.1CGEO\Downloads\W055S26\ABI020.shp" "C:\Users\diniz.1CGEO\Downloads\W055S26\ADA010.shp" "C:\Users\diniz.1CGEO\Downloads\W055S26\AEA010.shp" "C:\Users\diniz.1CGEO\Downloads\W055S26\AEB010.shp" "C:\Users\diniz.1CGEO\Downloads\W055S26\AEB020.shp" "C:\Users\diniz.1CGEO\Downloads\W055S26\AEC030.shp" "C:\Users\diniz.1CGEO\Downloads\W055S26\AGB005.shp" "C:\Users\diniz.1CGEO\Downloads\W055S26\AGB015.shp" "C:\Users\diniz.1CGEO\Downloads\W055S26\AGB045.shp" "C:\Users\diniz.1CGEO\Downloads\W055S26\AGB055.shp" "C:\Users\diniz.1CGEO\Downloads\W055S26\AGB075.shp" "C:\Users\diniz.1CGEO\Downloads\W055S26\AGB230.shp" "C:\Users\diniz.1CGEO\Downloads\W055S26\LAK190.shp" "C:\Users\diniz.1CGEO\Downloads\W055S26\LAL070.shp" "C:\Users\diniz.1CGEO\Downloads\W055S26\LAL260.shp" "C:\Users\diniz.1CGEO\Downloads\W055S26\LAN010.shp" "C:\Users\diniz.1CGEO\Downloads\W055S26\LAP010.shp" "C:\Users\diniz.1CGEO\Downloads\W055S26\LAP030.shp" "C:\Users\diniz.1CGEO\Downloads\W055S26\LAP050.shp" "C:\Users\diniz.1CGEO\Downloads\W055S26\LAQ040.shp" "C:\Users\diniz.1CGEO\Downloads\W055S26\LAQ063.shp" "C:\Users\diniz.1CGEO\Downloads\W055S26\LAQ070.shp" "C:\Users\diniz.1CGEO\Downloads\W055S26\LAQ130.shp" "C:\Users\diniz.1CGEO\Downloads\W055S26\LAT030.shp" "C:\Users\diniz.1CGEO\Downloads\W055S26\LBH030.shp" "C:\Users\diniz.1CGEO\Downloads\W055S26\LBH140.shp" "C:\Users\diniz.1CGEO\Downloads\W055S26\LBH165.shp" "C:\Users\diniz.1CGEO\Downloads\W055S26\LBH180.shp" "C:\Users\diniz.1CGEO\Downloads\W055S26\LBI020.shp" "C:\Users\diniz.1CGEO\Downloads\W055S26\LDB090.shp" "C:\Users\diniz.1CGEO\Downloads\W055S26\PAA012.shp" "C:\Users\diniz.1CGEO\Downloads\W055S26\PAC000.shp" "C:\Users\diniz.1CGEO\Downloads\W055S26\PAC030.shp" "C:\Users\diniz.1CGEO\Downloads\W055S26\PAD020.shp" "C:\Users\diniz.1CGEO\Downloads\W055S26\PAD030.shp" "C:\Users\diniz.1CGEO\Downloads\W055S26\PAF010.shp" "C:\Users\diniz.1CGEO\Downloads\W055S26\PAF040.shp" "C:\Users\diniz.1CGEO\Downloads\W055S26\PAJ110.shp" "C:\Users\diniz.1CGEO\Downloads\W055S26\PAK040.shp" "C:\Users\diniz.1CGEO\Downloads\W055S26\PAK170.shp" "C:\Users\diniz.1CGEO\Downloads\W055S26\PAL015.shp" "C:\Users\diniz.1CGEO\Downloads\W055S26\PAL020.shp" "C:\Users\diniz.1CGEO\Downloads\W055S26\PAL030.shp" "C:\Users\diniz.1CGEO\Downloads\W055S26\PAL241.shp" "C:\Users\diniz.1CGEO\Downloads\W055S26\PAM020.shp" "C:\Users\diniz.1CGEO\Downloads\W055S26\PAM030.shp" "C:\Users\diniz.1CGEO\Downloads\W055S26\PAM070.shp" "C:\Users\diniz.1CGEO\Downloads\W055S26\PAQ065.shp" "C:\Users\diniz.1CGEO\Downloads\W055S26\PAQ125.shp" "C:\Users\diniz.1CGEO\Downloads\W055S26\PAT042.shp" "C:\Users\diniz.1CGEO\Downloads\W055S26\PAT045.shp" "C:\Users\diniz.1CGEO\Downloads\W055S26\PBH070.shp" "C:\Users\diniz.1CGEO\Downloads\W055S26\PBH170.shp" "C:\Users\diniz.1CGEO\Downloads\W055S26\PBI010.shp" "C:\Users\diniz.1CGEO\Downloads\W055S26\PBI020.shp" "C:\Users\diniz.1CGEO\Downloads\W055S26\PGA034.shp" "C:\Users\diniz.1CGEO\Downloads\W055S26\PGB030.shp""   # Source Esri Shapefile(s)
- FEATURE_TYPES =
- DestDataset_POSTGIS = w055s26   # Database
- SourceDataset_POSTGIS = w055s26   # Database
- FEATURE_TYPES_2 = mgcp.aa010_a mgcp.aa010_p mgcp.aa012_a mgcp.aa012_p mgcp.aa040_p mgcp.aa050_p mgcp.aa052_a mgcp.ab000_a mgcp.ab010_a mgcp.ac000_a mgcp.ac000_p mgcp.ac020_p mgcp.ac030_a mgcp.ac030_p mgcp.ad010_a mgcp.ad010_p mgcp.ad020_p mgcp.ad030_a mgcp.ad030_p mgcp.ad050_a mgcp.ad050_p mgcp.af010_p mgcp.af020_l mgcp.af040_p mgcp.af070_p mgcp.ah025_l mgcp.ah050_a mgcp.ah050_p mgcp.ah070_p mgcp.ai030_a mgcp.aj010_a mgcp.aj030_a mgcp.aj030_p mgcp.aj050_p mgcp.aj051_p mgcp.aj110_a mgcp.aj110_p mgcp.ak030_a mgcp.ak040_a mgcp.ak040_p mgcp.ak060_a mgcp.ak090_a mgcp.ak100_a mgcp.ak120_a mgcp.ak130_l mgcp.ak150_l mgcp.ak150_p mgcp.ak160_a mgcp.ak160_p mgcp.ak170_a mgcp.ak170_p mgcp.ak180_a mgcp.ak190_a mgcp.ak190_l mgcp.al010_a mgcp.al012_a mgcp.al012_p mgcp.al015_a mgcp.al015_p mgcp.al019_a mgcp.al019_p mgcp.al020_a mgcp.al020_p mgcp.al025_p mgcp.al030_a mgcp.al030_p mgcp.al060_a mgcp.al060_l mgcp.al070_l mgcp.al099_p mgcp.al105_a mgcp.al105_p mgcp.al130_p mgcp.al140_a mgcp.al170_a mgcp.al200_a mgcp.al208_a mgcp.al210_l mgcp.al210_p mgcp.al241_p mgcp.al260_l mgcp.am010_a mgcp.am020_a mgcp.am020_p mgcp.am030_a mgcp.am030_p mgcp.am040_a mgcp.am040_p mgcp.am060_a mgcp.am060_p mgcp.am070_a mgcp.am070_p mgcp.an010_l mgcp.an050_l mgcp.an060_a mgcp.an075_p mgcp.an076_a mgcp.an076_p mgcp.ap010_l mgcp.ap030_l mgcp.ap050_l mgcp.aq040_a mgcp.aq040_l mgcp.aq063_l mgcp.aq065_p mgcp.aq070_l mgcp.aq070_p mgcp.aq075_l mgcp.aq090_p mgcp.aq110_p mgcp.aq113_l mgcp.aq116_a mgcp.aq116_p mgcp.aq125_a mgcp.aq125_p mgcp.aq130_a mgcp.aq130_l mgcp.aq135_a mgcp.aq140_a mgcp.at010_p mgcp.at030_l mgcp.at041_l mgcp.at042_p mgcp.at045_p mgcp.at050_a mgcp.at060_l mgcp.aux_moldura_a mgcp.aux_observacao_a mgcp.aux_observacao_l mgcp.aux_observacao_p mgcp.aux_revisao_a mgcp.aux_revisao_l mgcp.aux_revisao_p mgcp.aux_validacao_a mgcp.aux_validacao_l mgcp.aux_validacao_p mgcp.ba010_l mgcp.ba030_a mgcp.ba040_a mgcp.ba050_a mgcp.ba050_p mgcp.bb005_a mgcp.bb041_a mgcp.bb041_l mgcp.bb043_a mgcp.bb043_l mgcp.bb090_a mgcp.bb140_a mgcp.bb140_l mgcp.bb155_p mgcp.bb190_a mgcp.bb190_l mgcp.bb230_l mgcp.bb240_a mgcp.bd100_a mgcp.bd100_p mgcp.bd110_p mgcp.bd120_a mgcp.bd120_l mgcp.bd130_p mgcp.bd180_p mgcp.bh010_a mgcp.bh010_l mgcp.bh010_p mgcp.bh015_a mgcp.bh020_a mgcp.bh020_l mgcp.bh030_a mgcp.bh030_l mgcp.bh040_a mgcp.bh050_a mgcp.bh051_a mgcp.bh060_l mgcp.bh070_l mgcp.bh070_p mgcp.bh080_a mgcp.bh090_a mgcp.bh110_l mgcp.bh120_a mgcp.bh120_l mgcp.bh120_p mgcp.bh130_a mgcp.bh135_a mgcp.bh140_a mgcp.bh140_l mgcp.bh145_p mgcp.bh150_a mgcp.bh155_a mgcp.bh160_a mgcp.bh165_a mgcp.bh165_l mgcp.bh170_p mgcp.bh180_l mgcp.bh180_p mgcp.bi010_p mgcp.bi020_a mgcp.bi020_l mgcp.bi020_p mgcp.bi030_a mgcp.bi030_l mgcp.bi030_p mgcp.bi040_l mgcp.bi040_p mgcp.bi041_l mgcp.bi041_p mgcp.bi050_p mgcp.bj020_a mgcp.bj030_a mgcp.bj031_a mgcp.bj031_l mgcp.bj040_l mgcp.bj060_p mgcp.bj100_a mgcp.bj110_a mgcp.centroide_aa010_p mgcp.centroide_aa012_p mgcp.centroide_al020_p mgcp.centroide_ba030_p mgcp.centroide_ba040_p mgcp.centroide_bh010_p mgcp.centroide_bh015_p mgcp.centroide_bh020_p mgcp.centroide_bh030_p mgcp.centroide_bh080_p mgcp.centroide_bh090_p mgcp.centroide_bh120_p mgcp.centroide_bh130_p mgcp.centroide_bh135_p mgcp.centroide_bh140_p mgcp.centroide_bh150_p mgcp.centroide_bh160_p mgcp.centroide_bj020_p mgcp.centroide_bj030_p mgcp.centroide_bj100_p mgcp.centroide_bj110_p mgcp.centroide_da010_p mgcp.centroide_db170_p mgcp.centroide_ea010_p mgcp.centroide_ea040_p mgcp.centroide_ea050_p mgcp.centroide_ea055_p mgcp.centroide_eb010_p mgcp.centroide_eb020_p mgcp.centroide_ec010_p mgcp.centroide_ec030_p mgcp.centroide_ec040_p mgcp.centroide_ed010_p mgcp.centroide_ed020_p mgcp.centroide_ed030_p mgcp.centroide_zd020_p mgcp.da010_a mgcp.db010_l mgcp.db029_p mgcp.db061_a mgcp.db061_l mgcp.db070_l mgcp.db071_l mgcp.db090_a mgcp.db090_l mgcp.db100_l mgcp.db110_l mgcp.db115_a mgcp.db115_p mgcp.db150_p mgcp.db160_a mgcp.db160_l mgcp.db160_p mgcp.db170_a mgcp.db180_a mgcp.db180_p mgcp.db200_a mgcp.db200_l mgcp.delimitador_area_edificada_l mgcp.delimitador_area_sem_dados_l mgcp.delimitador_cobertura_do_solo_l mgcp.delimitador_elemento_hidrografico_l mgcp.delimitador_massa_dagua_l mgcp.ea010_a mgcp.ea020_l mgcp.ea040_a mgcp.ea050_a mgcp.ea055_a mgcp.eb010_a mgcp.eb020_a mgcp.ec010_a mgcp.ec020_a mgcp.ec030_a mgcp.ec030_l mgcp.ec030_p mgcp.ec040_a mgcp.ec060_a mgcp.ed010_a mgcp.ed020_a mgcp.ed030_a mgcp.fa015_a mgcp.fa090_l mgcp.fa100_a mgcp.ga034_p mgcp.gb005_a mgcp.gb015_a mgcp.gb030_p mgcp.gb035_a mgcp.gb040_p mgcp.gb045_a mgcp.gb050_l mgcp.gb050_p mgcp.gb055_a mgcp.gb065_a mgcp.gb065_p mgcp.gb075_a mgcp.gb220_p mgcp.gb230_a mgcp.gb230_p mgcp.gb485_p mgcp.su001_a mgcp.su001_p mgcp.zd020_a mgcp.zd040_p

Readers:
- SHAPEFILE_1: SHAPEFILE from $(SourceDataset_SHAPEFILE)
- POSTGIS_2: POSTGIS from $(SourceDataset_POSTGIS)

Writers:
- POSTGIS_1: POSTGIS to $(DestDataset_POSTGIS)

Note: banco de entrada
aa010_a (reader POSTGIS_2)
    attributes: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
PGB230 (reader SHAPEFILE_1)
    attributes: FCODE varchar(5), UID varchar(36), FUN long, ACC long, CCN varchar(254), SDV varchar(20), SDP varchar(254), SRT long, TXT varchar(254), AOO double, BAC long, BOT long, BSC long, CAA long, CAB long, CCT long, CDA long, COD long, CON long, CRA long, CRM long, CSP long, DMB double, DMT double, FFN long, FFP long, FIC long, FMM long, FPT long, FUC long,
      GAW double, HAF long, HCT long, HGT double, HWT long, HYP long, IKO varchar(254), LEN double, LFA long, LOC long, LTN long, MCC long, MES long, NAM varchar(80), NFI varchar(18), NFN varchar(18), NOS long, NST long, OHB double, ORD long, PPC long, PPO long, PRM long, RAC long, REL long, RGC long, RIR long, RRA long, RRC long, RST long,
      RTA long, RWC long, SCC long, SEP long, SFS long, SMC long, SSC long, SWT long, TID long, TOS long, TRE long, TRS long, TTC long, TUC long, VEG long, VOI varchar(36), VSP long, WCC long, WD1 double, WID double, WLE long, WST long, WTC long, ZVA double
    -> BulkAttributeRenamer
BulkAttributeRenamer
    ATTRCHOICE = All Attributes
    CASE_CHANGE_TYPE = lower
    MODE_CHOICE = RENAME
    PATTERN_ACTION_DISP = CASECHANGE
    -> StringCaseChanger
StringCaseChanger
    ATTRCHOICE = Selected Attributes
    ATTRLIST = fme_feature_type
    CHANGE_TYPE = lowercase
    -> p
p: Tester
    BOOL_OP = OR
    TEST_CLAUSE = CASE_INSENSITIVE_TEST @Value(fme_feature_type) BEGINS_WITH p
    TEST_MODE = CASE_INSENSITIVE_TEST
    PASSED -> p_2
    FAILED -> l
p_2: AttributeCreator
    ATTR_TABLE = SET_TO fme_feature_type (varchar(50)) = @Substring(@Value(fme_feature_type),1)_p
    -> CoordinateSystemSetter
l: Tester
    BOOL_OP = OR
    TEST_CLAUSE = CASE_INSENSITIVE_TEST @Value(fme_feature_type) BEGINS_WITH l
    TEST_MODE = CASE_INSENSITIVE_TEST
    PASSED -> l_2
    FAILED -> a
l_2: AttributeCreator
    ATTR_TABLE = SET_TO fme_feature_type (varchar(50)) = @Substring(@Value(fme_feature_type),1)_l
    -> CoordinateSystemSetter
a: Tester
    BOOL_OP = OR
    TEST_CLAUSE = CASE_INSENSITIVE_TEST @Value(fme_feature_type) BEGINS_WITH a
    TEST_MODE = CASE_INSENSITIVE_TEST
    PASSED -> a_2
    FAILED -> ERROR
a_2: AttributeCreator
    ATTR_TABLE = SET_TO fme_feature_type (varchar(50)) = @Substring(@Value(fme_feature_type),1)_a
    -> CoordinateSystemSetter
CoordinateSystemSetter
    COORDSYS = EPSG:4326
    -> AttributeCreator
AttributeCreator
    ATTR_TABLE = SET_TO fme_feature_type (varchar(50)) = mgcp.@Value(fme_feature_type)
    -> UniqueIdentifierGenerator
UniqueIdentifierGenerator
    UUID_ATTR = id
    UUID_FORMAT = UUID_ONLY
    -> Table1 (writer POSTGIS_1)
Table1 (writer POSTGIS_1)
ERROR: Inspector
