FME workspace conversao_postgis30_postgistrd4.fmw

Parameters:
- DestDataset_POSTGIS_2 =
- FEATURE_TYPES =
- FEATURE_TYPES_2 =
- FEATURE_TYPES_3 =
- JsonMapeamento =
- SourceDataset_POSTGIS =
- SourceDataset_POSTGIS_6 =
- direcao =
- postgis_sql_where_clause =

Readers:
- POSTGIS_1: POSTGIS from $(SourceDataset_POSTGIS_6)
- POSTGIS_2: POSTGIS from $(SourceDataset_POSTGIS)
- POSTGIS_3: POSTGIS from $(DestDataset_POSTGIS_2)

Writers:
- POSTGIS_5: POSTGIS to $(DestDataset_POSTGIS_2)
- POSTGIS_4: POSTGIS to $(DestDataset_POSTGIS_2)

Note: TRD4
aaa010 (reader POSTGIS_3)
    attributes: id serial, ppo int2, nfn varchar(255), nfi varchar(255), nam varchar(255), fun int2, mzn int2, acc int2, ccn varchar(255), sdv varchar(255), sdp varchar(255), srt int2, txt varchar(255), uid varchar(255), afa int2, aoo float4, atc int2, azc int2, bac int2, bloco varchar(255), boc int2, bot int2, bsc int2, caa int2, cab int2, cat int2, categoria varchar(255), cct int2, cda int2, cns int2,
      cod int2, con int2, corrigido int2, cra int2, crm int2, csp int2, dmb float4, dmt float4, eet int2, fac int2, ffn int2, ffp int2, fhc int2, fic int2, fmm int2, fpt int2, frt int2, fuc int2, gaw float4, gnc int2, haf int2, hct int2, hgt float4, hwt int2, hyp int2, iko varchar(255), len float4, lfa int2, loc int2, ltn int4,
      mcc int2, mes int2, mi varchar(255), na2 varchar(255), nome varchar(255), nos int4, nst int2, obs varchar(255), ohb float4, opc int2, ord int2, pby int2, ppc int2, prm int2, pwc int2, rac int2, ray int2, rel int2, rgc int2, rir int2, rkf int2, rra int2, rrc int2, rsa int2, rst int2, rta int2, rwc int2, scc int2, sdo float4, sdt int2,
      sep int2, sfs int2, slt int2, smc int2, ssc int2, sta int2, suc int2, sujeito_inundacao int2, swt int2, tid int2, tipo int2, tos int2, tre int2, trs int2, ttc int2, tuc int2, veg int2, vgt int2, voi varchar(255), vsp int2, wcc int2, wd1 float4, wft int2, wid float4, wle int2, wst int2, wtc int2, zva float4
    -> Tester_3
Tester_3
    BOOL_OP = OR
    COMPOSITE_TEST = 1
    TEST_CLAUSE = TEST @Value(fme_feature_type) = mgcp.aux_moldura_a
    TEST_MODE = TEST
    PASSED -> Clipper [CLIPPER]
Note: edgv_30_puro
aer_pista_ponto_pouso_a (reader POSTGIS_1)
    attributes: id serial, nome varchar(255), geometriaaproximada bool, tipopista int2, revestimento int2, usopista int2, homologacao int2, operacional int2, situacaofisica int2, largura float4, extensao float4, altitude float4, acostamento int2, administracao int2, altitudegeometrica float4, altitudeortometrica float4, altura float4, alturaaproximada float4, alturaestimada float4, alturalamina float4, alturatorreaer float4, anocriacao varchar(4), anodereferencia int4, antropizada int2, aptidaooperacional int2, arealegal float4, areaoficial varchar(15), areavalvulas int2, artificial int2, atividade int2,
      atolegal varchar(100), bitola int2, bombeamento int2, calado float4, caladomaxseca float4, calcada int2, canteirodivisorio int2, cargasuportmaxima float4, causa int2, causaexposicao int2, ceg varchar(16), centrodecarga int2, chamine int2, classeativecon int2, classificacao varchar(100), classificacaoporte int2, codequipdesenvsocial varchar(80), codestacao varchar(50), codident varchar(80), codidentificadorunico varchar(50), codigo varchar(9), codiso3166 varchar(3), codponto varchar(12), codtrechoferrov varchar(25), codtrechorod varchar(25), coletiva int2, concessionaria varchar(100), cota int4, cotacomprovada bool, crista int2,
      cultivopredominante int2, cultura int2, datamedicao varchar(10), datasituacaojuridica varchar(10), datavisita varchar(10), denominacaoassociada int2, densidade int2, depressao bool, desnivel float4, destinacaocemiterio int2, destinadoa int2, divisaoativecon int2, dominialidade int2, eletrificada int2, emarruamento bool, emduto int2, encoberto bool, ensino int2, escala varchar(255), especie int2, especiepredominante int2, estadofisico int2, extensaotrecho float4, finalidade int2, finalidadedep int2, finalidadepatio int2, fixa bool, formaextracao int2, formarocha int2, gabhorizsup float4,
      gabvertsup float4, geocodigo varchar(15), grupoativecon int2, grupoetnico varchar(100), historicomodificacoes varchar(255), identificador varchar(80), idtsub int4, inom varchar(255), isolada int2, jurisdicao int2, largurafaixaservidao float4, larguramedia float4, latitude varchar(16), limitevelocidade float4, localizacaoequipdesenvsocial int2, longitude varchar(16), matcondutor int2, matconstr int2, materialpredominante int2, mattransp int2, meiofio int2, mi varchar(255), modalidade int2, modaluso int2, navegavel int2, necessitamanutencao int2, nivelatencao int2, nomelocal varchar(80), nrdutos int4, nrfaixas int4,
      nrlinhas int2, nrpistas int4, obs varchar(255), orgaoenteresp varchar(15), outrarefalt varchar(20), outrarefplan varchar(20), ovgd int2, pavimentacao int2, perimetrooficial float4, periodicidadeinunda varchar(20), pesosuportmaximo float4, posicaopista int2, posicaorelativa int2, posicaoreledific int2, possuitrechodrenagem bool, potenciaout float4, procextracao int2, profundidade int4, proprioadm int2, proximidade int2, publico int2, qualidagua int2, redereferencia int2, referencialaltim int2, referencialgrav int2, regime int2, religiao varchar(100), salgada int2, sarjeta int2, secaoativecon int2,
      secundaria int2, setor int2, sigla varchar(80), sin int2, sistemageodesico int2, situacaoagua int2, situacaocosta int2, situacaoemagua int2, situacaoespacial int2, situacaojuridica int2, situacaomarco int2, terreno int2, tipoahe int2, tipoalterantrop int2, tipoarea int2, tipoareaumida int2, tipoassociado int2, tipoatracad int2, tipobanco int2, tipocaminhoaereo int2, tipocampo int2, tipocampoquadra int2, tipocemiterio int2, tipocombustivel int2, tipoconteudo int2, tipocurvanivel int2, tipodelimfis int2, tipodepgeral int2, tipoedifabast int2, tipoedifaero int2,
      tipoedifagropec int2, tipoedifcomercserv int2, tipoedifcomunic int2, tipoedifenergia int2, tipoediflazer int2, tipoedifmetroferrov int2, tipoedifport int2, tipoedifpubcivil int2, tipoedifrelig int2, tipoedifrod int2, tipoedifsaneam int2, tipoedifturist int2, tipoelemnat int2, tipoelevador int2, tipoembarcacao int2, tipoentroncamento int2, tipoequipagropec int2, tipoequipdesenvsocial int2, tipoestgerad int2, tipoexposicao int2, tipoextmin int2, tipofontedagua int2, tipofundeadouro int2, tipoilha int2, tipoinstalmilitar int2, tipolavoura int2, tipolimpol int2, tipolocalidade int2, tipomanguezal int2, tipomarcolim int2,
      tipomassadagua int2, tipoobst int2, tipopassagviad int2, tipopavimentacao int2, tipopistacomp int2, tipoplataforma int2, tipopocomina int2, tipoponte int2, tipoposte int2, tipopostofisc int2, tipoproduto int2, tipoprodutoresiduo int2, tipoptoestmed int2, tipoptorefgeodtopo int2, tipoquebramolhe int2, tipoqueda int2, tiporecife int2, tiporef int2, tiporepdiplomatica int2, tiposinal int2, tiposumvert int2, tipoterrexp int2, tipotravessia int2, tipotravessiaped int2, tipotrechocomunic int2, tipotrechodrenagem int2, tipotrechoduto int2, tipotrechoferrov int2, tipotunel int2, tipounidprotegida int2,
      tipounidprotinteg int2, tipounidusosust int2, tipouso int2, tipousocaminhoaer int2, tipousoedif int2, tipoveg int2, tipovia int2, tombada int2, trafego int2, tratamento int2, trechoemperimetrourbano int2, turistica int2, unidadevolume int2, usoprincipal int2, valorgravidade float4, valorvolume float4, vaolivrehoriz float4, vaovertical float4, vereda int2
    -> Tester_2
aer_pista_ponto_pouso_a (reader POSTGIS_2)
    attributes: id uuid, nome varchar(255), geometriaaproximada bool, tipopista int2, revestimento int2, usopista int2, homologacao int2, operacional int2, situacaofisica int2, largura float4, extensao float4, altitude float4, observacao varchar(255), acostamento int2, administracao int2, altitudegeometrica float4, altitudeortometrica float4, altura float4, alturaaproximada float4, alturaestimada float4, alturalamina float4, alturatorreaer float4, anocriacao varchar(4), anodereferencia int4, antropizada int2, aptidaooperacional int2, arealegal float4, areaoficial varchar(15), areavalvulas int2, artificial int2,
      atividade int2, atolegal varchar(255), bitola int2, bombeamento int2, calado float4, caladomaxseca float4, calcada int2, canteirodivisorio int2, cargasuportmaxima float4, causa int2, causaexposicao int2, ceg varchar(16), centrodecarga int2, chamine int2, classeativecon int2, classificacao varchar(255), classificacaoporte int2, codequipdesenvsocial varchar(255), codestacao varchar(50), codident varchar(255), codidentificadorunico varchar(50), codigo varchar(9), codiso3166 varchar(3), codponto varchar(12), codtrechoferrov varchar(25), codtrechorod varchar(25), coletiva int2, concessionaria varchar(255), cota int4, cotacomprovada bool,
      crista int2, cultivopredominante int2, cultura int2, datamedicao varchar(10), datasituacaojuridica varchar(10), datavisita varchar(10), denominacaoassociada int2, densidade int2, depressao bool, desnivel float4, destinacaocemiterio int2, destinadoa int2, divisaoativecon int2, dominialidade int2, eletrificada int2, emarruamento bool, emduto int2, encoberto bool, ensino int2, escala varchar(255), especie int2, especiepredominante int2, estadofisico int2, extensaotrecho float4, finalidade int2, finalidadedep int2, finalidadepatio int2, fixa bool, formaextracao int2, formarocha int2,
      gabhorizsup float4, gabvertsup float4, geocodigo varchar(15), grupoativecon int2, grupoetnico varchar(255), historicomodificacoes varchar(255), identificador varchar(255), idtsub int4, inom varchar(255), isolada int2, jurisdicao int2, largurafaixaservidao float4, larguramedia float4, latitude varchar(16), limitevelocidade float4, localizacaoequipdesenvsocial int2, longitude varchar(16), matcondutor int2, matconstr int2, materialpredominante int2, mattransp int2, meiofio int2, mi varchar(255), modalidade int2, modaluso int2, navegavel int2, necessitamanutencao int2, nivelatencao int2, nomelocal varchar(255), nrdutos int4,
      nrfaixas int4, nrlinhas int2, nrpistas int4, obs varchar(255), orgaoenteresp varchar(255), outrarefalt varchar(255), outrarefplan varchar(255), ovgd int2, pavimentacao int2, perimetrooficial float4, periodicidadeinunda varchar(20), pesosuportmaximo float4, posicaopista int2, posicaorelativa int2, posicaoreledific int2, possuitrechodrenagem bool, potenciaout float4, procextracao int2, profundidade int4, proprioadm int2, proximidade int2, publico int2, qualidagua int2, redereferencia int2, referencialaltim int2, referencialgrav int2, regime int2, religiao varchar(255), salgada int2, sarjeta int2,
      secaoativecon int2, secundaria int2, setor int2, sigla varchar(255), sin int2, sistemageodesico int2, situacaoagua int2, situacaocosta int2, situacaoemagua int2, situacaoespacial int2, situacaojuridica int2, situacaomarco int2, terreno int2, tipoahe int2, tipoalterantrop int2, tipoarea int2, tipoareaumida int2, tipoassociado int2, tipoatracad int2, tipobanco int2, tipocaminhoaereo int2, tipocampo int2, tipocampoquadra int2, tipocemiterio int2, tipocombustivel int2, tipoconteudo int2, tipocurvanivel int2, tipodelimfis int2, tipodepgeral int2, tipoedifabast int2,
      tipoedifaero int2, tipoedifagropec int2, tipoedifcomercserv int2, tipoedifcomunic int2, tipoedifenergia int2, tipoediflazer int2, tipoedifmetroferrov int2, tipoedifport int2, tipoedifpubcivil int2, tipoedifrelig int2, tipoedifrod int2, tipoedifsaneam int2, tipoedifturist int2, tipoelemnat int2, tipoelevador int2, tipoembarcacao int2, tipoentroncamento int2, tipoequipagropec int2, tipoequipdesenvsocial int2, tipoestgerad int2, tipoexposicao int2, tipoextmin int2, tipofontedagua int2, tipofundeadouro int2, tipoilha int2, tipoinstalmilitar int2, tipolavoura int2, tipolocalidade int2, tipomanguezal int2, tipomarcolim int2,
      tipomassadagua int2, tipoobst int2, tipopassagviad int2, tipopavimentacao int2, tipopistacomp int2, tipoplataforma int2, tipopocomina int2, tipoponte int2, tipoposte int2, tipopostofisc int2, tipoproduto int2, tipoprodutoresiduo int2, tipoptoestmed int2, tipoptorefgeodtopo int2, tipoquebramolhe int2, tipoqueda int2, tiporecife int2, tiporef int2, tiporepdiplomatica int2, tiposinal int2, tiposumvert int2, tipoterrexp int2, tipotravessia int2, tipotravessiaped int2, tipotrechocomunic int2, tipotrechodrenagem int2, tipotrechoduto int2, tipotrechoferrov int2, tipotunel int2, tipounidprotegida int2,
      tipounidprotinteg int2, tipounidusosust int2, tipouso int2, tipousocaminhoaer int2, tipousoedif int2, tipoveg int2, tipovia int2, tombada int2, trafego int2, tratamento int2, trechoemperimetrourbano int2, turistica int2, unidadevolume int2, usoprincipal int2, valorgravidade float4, valorvolume float4, vaolivrehoriz float4, vaovertical float4, vereda int2
    -> Tester_2
Tester_2
    BOOL_OP = OR
    TEST_CLAUSE:
      TEST @Value(fme_feature_type) = edgv.rel_curva_nivel_l
      TEST @Value(fme_feature_type) = edgv.rel_ponto_cotado_altimetrico_p
      TEST @Value(fme_feature_type) = edgv.aux_moldura_a
      TEST @Value(fme_feature_type) = edgv.hid_banco_areia_a
      TEST @Value(fme_feature_type) = edgv.lml_limite_politico_administrativo_l
      TEST @Value(fme_feature_type) = edgv.lml_terra_indigena_a
      TEST @Value(fme_feature_type) = edgv.lml_unidade_conservacao_a
    TEST_MODE = TEST
    FAILED -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Reprojector
Reprojector
    DEST = EPSG:4326
    INTERPOLATION_TYPE_NAME = Nearest Neighbor
    RASTER_CELL_SIZE = Preserve Cells
    RASTER_TOLERANCE = 0.0
    REPROJECTED -> Clipper [CLIPPEE]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryValidator
GeometryValidator
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme CONSECUTIVE_IDENTICAL_VERTICES_2D CHECK_Z]YES]FME_CONTROLLER_QUERY_FILE]transformers/dependencies/geometryvalidator8/CONSECUTIVE_IDENTICAL_VERTICES_2D.fme MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme NULL_REMOVAL FME_CONTROLLER_QUERY_FILE]transformers/dependencies/geometryvalidator8/NULL_REMOVAL.fme]FME_CONTROLLER_CHOICE]NULL_REMOVAL OGC_SIMPLE_CHECK LEGACY_OGC]No]FME_CONTROLLER_QUERY_FILE]transformers/dependencies/geometryvalidator8/OGC_SIMPLE_CHECK.fme OGC_VALID_CHECK OGC_VERSION]V1.2.0]FME_CONTROLLER_QUERY_FILE]transformers/dependencies/geometryvalidator8/OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers/dependencies/geometryvalidator8/PLANAR_SURFACE.fme SELF_INTERSECTING CHECK_HOLE_TOUCHING_POLYGON]No]CONNECT_Z_MODE_SI]FIRST_WINS]SELF_INTERSECTION_TOLERANCE]None]FME_CONTROLLER_QUERY_FILE]transformers/dependencies/geometryvalidator8/SELF_INTERSECTING.fme SHELL_VALIDATION FLIP_APPEARANCE_MODE]FLIP_APPEARANCES]FME_CONTROLLER_QUERY_FILE]transformers/dependencies/geometryvalidator8/SHELL_VALIDATION.fme SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]0.0]FME_CONTROLLER_QUERY_FILE]transformers/dependencies/geometryvalidator8/TYPE_REPAIR.fme MISMATCHED_DIMENSIONS FORCE_DIMENSION]2D]FME_CONTROLLER_QUERY_FILE]transformers/dependencies/geometryvalidator8/MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers/dependencies/geometryvalidator8/MISSING_MEASURES_AND_ELEVATIONS.fme SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> GeometryFilter
    FAILED -> GeometryFilter
    REPAIRED -> GeometryFilter
GeometryFilter
    BREAK_AGG = No
    GEOM_PORT_NAMES = Point Line Area
    POINT -> Junction
    LINE -> Junction
    AREA -> Junction
Junction
    -> PythonCaller_EDGV30_TRD
Note: mapeamento
PythonCaller_EDGV30_TRD
    NEW_ATTRIBUTES = CLASS_NOT_FOUND
    PYTHONSOURCE:
      import fme
      import fmeobjects
      import copy
      import sys
      import os
      import json

      class FeatureProcessor(object):
          def __init__(self):
              self.mappingDict = self.buildFileDict(FME_MacroValues['JsonMapeamento'])
              self.mappingType = FME_MacroValues['direcao']

          def buildFileDict(self, mappingPath):
              with open(mappingPath, 'r', encoding='utf-8') as file:
                  mapDict = json.loads(file.read())
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          if feature.getAttribute(attr) == 'f':
                              featDict[attr] = 'False'
                          elif feature.getAttribute(attr) == 't':
                              featDict[attr] = 'True'
                          else:
                              featDict[attr] = feature.getAttribute(attr)
                      else:
                          featDict[attr] = None
              if feature.performFunction('@GeometryType()') == 'fme_polygon' or feature.performFunction('@GeometryType()') == 'fme_donut':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              else:
                   featDict["INVALID_GEOM"] = True
              return featDict

          def evaluateExpression(self, featDict, expression):
              if not expression["nome_atributo"] in featDict:
                  return False
              if expression["valor"] is None or expression["valor"] == "":
                  return featDict[expression["nome_atributo"]] is None or featDict[expression["nome_atributo"]] == ""
              else:
                  return u"{0}".format(featDict[expression["nome_atributo"]]) == u"{0}".format(expression["valor"])

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "ida":
                  key_attr_origin = "attr_ida"
                  key_attr_destiny = "attr_volta"
                  key_value_origin = "valor_ida"
                  key_value_destiny = "valor_volta"
                  key_default = "atributos_default_ida"
                  key_filter = "filtro_ida"
                  key_class_origin = "classe_ida"
                  key_class_destiny = "classe_volta"
                  key_group_origin = "tupla_ida"
                  key_group_destiny = "tupla_volta"
                  key_affix_origin = "afixo_geom_ida"
                  key_affix_destiny = "afixo_geom_volta"
                  key_schema_origin = "schema_ida"
                  key_schema_destiny = "schema_volta"
                  key_class_affix_origin = "com_afixo_geom_ida"
                  key_class_affix_destiny = "com_afixo_geom_volta"
                  key_class_schema_origin = "com_schema_ida"
                  key_class_schema_destiny = "com_schema_volta"
                  key_agregar = "agregar_geom_ida"
              else:
                  key_attr_origin = "attr_volta"
                  key_attr_destiny = "attr_ida"
                  key_value_origin = "valor_volta"
                  key_value_destiny = "valor_ida"
                  key_default = "atributos_default_volta"
                  key_filter = "filtro_volta"
                  key_class_origin = "classe_volta"
                  key_class_destiny = "classe_ida"
                  key_group_origin = "tupla_volta"
                  key_group_destiny = "tupla_ida"
                  key_affix_origin = "afixo_geom_volta"
                  key_affix_destiny = "afixo_geom_ida"
                  key_schema_origin = "schema_volta"
                  key_schema_destiny = "schema_ida"
                  key_class_affix_origin = "com_afixo_geom_volta"
                  key_class_affix_destiny = "com_afixo_geom_ida"
                  key_class_schema_origin = "com_schema_volta"
                  key_class_schema_destiny = "com_schema_ida"
                  key_agregar = "agregar_geom_volta"

              featDict["fme_feature_type_original"] = featDict["fme_feature_type"]

              if key_schema_origin in self.mappingDict and self.mappingDict[key_schema_origin]:
                  featDict["fme_feature_type"] = featDict["fme_feature_type"][len(self.mappingDict[key_schema_origin])+1:]

              featDict["fme_feature_type_sem_schema"] = featDict["fme_feature_type"]

              if key_affix_origin in self.mappingDict and 'tipo' in self.mappingDict[key_affix_origin] and self.mappingDict[key_affix_origin]['tipo'] == 'sufixo':
                  featDict["fme_feature_type"] = featDict["fme_feature_type"][:-len(self.mappingDict[key_affix_origin][featDict["$GEOM_TYPE"]])]
                  featDict["fme_feature_type_sem_afixo"] = featDict["fme_feature_type_original"][:-len(self.mappingDict[key_affix_origin][featDict["$GEOM_TYPE"]])]

              if key_affix_origin in self.mappingDict and 'tipo' in self.mappingDict[key_affix_origin] and self.mappingDict[key_affix_origin]['tipo'] == 'prefixo':
                  featDict["fme_feature_type"] = featDict["fme_feature_type"][len(self.mappingDict[key_affix_origin][featDict["$GEOM_TYPE"]]):]
                  featDict["fme_feature_type_sem_afixo"] = featDict["fme_feature_type_original"][len(self.mappingDict[key_affix_origin][featDict["$GEOM_TYPE"]]):]

              should_map = False
              for classmap in self.mappingDict['mapeamento_classes']:
                  if "sentido" not in classmap or ("sentido" in classmap and classmap["sentido"] == self.mappingType):
                      if key_class_affix_origin in classmap and classmap[key_class_affix_origin] and key_class_schema_origin in classmap and classmap[key_class_schema_origin]:
                          class_name = featDict["fme_feature_type_original"]
                      elif key_class_affix_origin in classmap and classmap[key_class_affix_origin]:
                          class_name = featDict["fme_feature_type_sem_schema"]
                      elif key_class_schema_origin in classmap and classmap[key_class_schema_origin]:
                          class_name = featDict["fme_feature_type_sem_afixo"]
                      else:
                           class_name = featDict["fme_feature_type"]

                      if classmap[key_class_origin] == class_name:
                          if key_filter in classmap:
                              if not self.evaluateFilter(featDict, classmap[key_filter]):
                                  continue
                          should_map = True
              if not should_map:
                  featDict["CLASS_NOT_FOUND"] = True
                  return featDict

              mappedFeat = copy.deepcopy(featDict)

              if key_default in self.mappingDict:
                  for default in self.mappingDict[key_default]:
                      mappedFeat[default["nome_atributo"]] = default["valor"]

              if 'mapeamento_atributos' in self.mappingDict:
                  for attmap in self.mappingDict['mapeamento_atributos']:
                      if attmap[key_attr_origin] in mappedFeat:
                          mappedFeat[attmap[key_attr_destiny]] = featDict[attmap[key_attr_origin]]
                          if "traducao" in attmap:
                              for valuemap in attmap["traducao"]:
                                  if u"{0}".format(valuemap[key_value_origin]) == u"{0}".format(featDict[attmap[key_attr_origin]]) and ("sentido" not in valuemap or ("sentido" in valuemap and valuemap["sentido"] == self.mappingType)):
                                      mappedFeat[attmap[key_attr_destiny]] = valuemap[key_value_destiny]

              if "mapeamento_multiplo" in self.mappingDict:
                  for attmap in self.mappingDict['mapeamento_multiplo']:
                      if "sentido" not in attmap or ("sentido" in attmap and attmap["sentido"] == self.mappingType):
                          if all([self.evaluateExpression(featDict, condition) for condition in attmap[key_group_origin]]):
                              for valuemap in attmap[key_group_destiny]:
                                  if "concatenar" in valuemap and valuemap["concatenar"] and valuemap["nome_atributo"] in mappedFeat and mappedFeat[valuemap["nome_atributo"]]:
                                      mappedFeat[valuemap["nome_atributo"]] = mappedFeat[valuemap["nome_atributo"]] + ' | ' + valuemap["valor"]
                                  else:
                                      mappedFeat[valuemap["nome_atributo"]] = valuemap["valor"]

              if 'mapeamento_classes' in self.mappingDict:
                  for classmap in self.mappingDict['mapeamento_classes']:
                      if "sentido" not in classmap or ("sentido" in classmap and classmap["sentido"] == self.mappingType):
                          if key_class_affix_origin in classmap and classmap[key_class_affix_origin] and key_class_schema_origin in classmap and classmap[key_class_schema_origin]:
                              class_name = featDict["fme_feature_type_original"]
                          elif key_class_affix_origin in classmap and classmap[key_class_affix_origin]:
                              class_name = featDict["fme_feature_type_sem_schema"]
                          elif key_class_schema_origin in classmap and classmap[key_class_schema_origin]:
                              class_name = featDict["fme_feature_type_sem_afixo"]
                          else:
                              class_name = featDict["fme_feature_type"]

                          if classmap[key_class_origin] == class_name:
                              if key_filter in classmap:
                                  if not self.evaluateFilter(featDict, classmap[key_filter]):
                                      continue

                              mappedFeat["fme_feature_type"] = classmap[key_class_destiny]

                              if key_class_affix_destiny in classmap and classmap[key_class_affix_destiny]:
                                  pass
                              elif key_affix_destiny in self.mappingDict and 'tipo' in self.mappingDict[key_affix_destiny]:
                                  if self.mappingDict[key_affix_destiny]['tipo'] == 'sufixo':
                                      mappedFeat["fme_feature_type"] = mappedFeat["fme_feature_type"] + self.mappingDict[key_affix_destiny][featDict["$GEOM_TYPE"]]

                                  if self.mappingDict[key_affix_destiny]['tipo'] == 'prefixo':
                                      mappedFeat["fme_feature_type"] = self.mappingDict[key_affix_destiny][featDict["$GEOM_TYPE"]] + mappedFeat["fme_feature_type"]

                              if key_class_schema_destiny in classmap and classmap[key_class_schema_destiny]:
                                  pass
                              elif key_schema_destiny in self.mappingDict and self.mappingDict[key_schema_destiny]:
                                  mappedFeat["fme_feature_type"] = self.mappingDict[key_schema_destiny] + '.' + mappedFeat["fme_feature_type"]


                              if key_default in classmap:
                                  for default in classmap[key_default]:
                                      mappedFeat[default["nome_atributo"]] = default["valor"]

                              if "mapeamento_atributos" in classmap:
                                  for attmap in classmap['mapeamento_atributos']:
                                      if attmap[key_attr_origin] in featDict:
                                          if attmap[key_attr_destiny] not in mappedFeat:
                                              mappedFeat[attmap[key_attr_destiny]] = featDict[attmap[key_attr_origin]]
                                          if "traducao" in attmap:
                                              for valuemap in attmap["traducao"]:
                                                  if u"{0}".format(valuemap[key_value_origin]) == u"{0}".format(featDict[attmap[key_attr_origin]]) and ("sentido" not in valuemap or ("sentido" in valuemap and valuemap["sentido"] == self.mappingType)):
                                                      mappedFeat[attmap[key_attr_destiny]] = valuemap[key_value_destiny]

                              if "mapeamento_multiplo" in classmap:
                                  for attmap in classmap['mapeamento_multiplo']:
                                      if "sentido" not in attmap or ("sentido" in attmap and attmap["sentido"] == self.mappingType):
                                          if all([self.evaluateExpression(featDict, condition) for condition in attmap[key_group_origin]]):
                                              for valuemap in attmap[key_group_destiny]:
                                                  if "concatenar" in valuemap and valuemap["concatenar"] and valuemap["nome_atributo"] in mappedFeat and mappedFeat[valuemap["nome_atributo"]]:
                                                      mappedFeat[valuemap["nome_atributo"]] = mappedFeat[valuemap["nome_atributo"]] + ' | ' + valuemap["valor"]
                                                  else:
                                                      mappedFeat[valuemap["nome_atributo"]] = valuemap["valor"]

                              if key_agregar in classmap:
                                  mappedFeat["AGGREGATE_GEOM"] = classmap[key_agregar]
                              elif key_agregar in self.mappingDict:
                                  mappedFeat["AGGREGATE_GEOM"] = self.mappingDict[key_agregar]

                              break

              return mappedFeat

          def mapDictToFeature(self, feat, featDict):
              for attr, value in featDict.items():
                  if value == 'True':
                      feat.setAttribute(attr, 1)
                  elif value == 'False':
                      feat.setAttribute(attr, 0)
                  elif value or value == 0:
                      feat.setAttribute(attr, u'{0}'.format(value))
                  else:
                      feat.setAttributeNullWithType(attr,0)
              if "AGGREGATE_GEOM" in featDict and featDict["AGGREGATE_GEOM"]:
                  feat.buildAggregateFeat([feat])
              return feat

          def input(self,feature):
              if feature.performFunction('@GeometryType()') == 'fme_aggregate':
                  features = feature.splitAggregate(True)
              else:
                  features = [feature]
              for simple_feature in features:
                  feat = self.buildFeatureDict(simple_feature)
                  if "INVALID_GEOM" in feat and feat["INVALID_GEOM"]:
                      simple_feature.setAttribute("INVALID_GEOM", u'True')
                      self.pyoutput(simple_feature)
                      continue

                  outputFeatDict = self.convertFeature(feat)
                  if "CLASS_NOT_FOUND" in outputFeatDict and not outputFeatDict["CLASS_NOT_FOUND"]:
                      simple_feature.setAttribute("CLASS_NOT_FOUND", u'True')
                      self.pyoutput(simple_feature)
                  else:
                      outputFeature = self.mapDictToFeature(simple_feature, outputFeatDict)
                      self.pyoutput(outputFeature)

          def close(self):
              pass
    PYTHONSYMBOL = FeatureProcessor
    -> PythonCaller_TRD_EDGV30_Output
    -> Tester_4
PythonCaller_TRD_EDGV30_Output: Inspector
    TACKATTRS = fme_feature_type
Note: Teste de mapeamento
Tester_4
    BOOL_OP = OR
    TEST_CLAUSE = TEST @Value(CLASS_NOT_FOUND) = True
    TEST_MODE = TEST
    PASSED -> UUIDGenerator_2
    PASSED -> Sampler
    FAILED -> UUIDGenerator
Sampler
    GROUP_BY = fme_feature_type
    RATE = 1
    SAMPLE_MODE = No
    SAMPLE_TYPE_LONG = First N Features
    SAMPLED -> AttributeKeeper
AttributeKeeper
    CREATE_BULK_MODE_FEATURES = NO
    KEEP_ATTRS = fme_feature_type,id,fft
UUIDGenerator_2
    UUID_ATTR = controle_uuid
    -> AttributeCreator
AttributeCreator
    ATTR_TABLE:
      SET_TO descricao = @Value(fme_feature_type)
      SET_TO corrigido = false
      SET_TO obs = classe: @Value(fme_feature_type) - id: @Value(id)
    -> GeometryRefiner
GeometryRefiner
    -> GeometryFilter_2
GeometryFilter_2
    BREAK_AGG = No
    GEOM_PORT_NAMES = Point Line Area
    POINT -> Counter
    LINE -> Counter_2
    AREA -> Counter_3
    <UNFILTERED> -> GEOMETRIA_INVALIDA
Counter
    CNT_ATTR = _count
    DOMAIN = counter
    SCOPE = Global
    START = 0
    -> Aggregator
Aggregator
    ACCUM_ATTRS_NAME = Use Attributes From One Feature
    AGGREGATE_TYPE = Homogeneous Collection (If Possible)
    GROUP_BY = _count
    MODE = Geometry - Assemble One Level
    SEP = ,
    AGGREGATE -> aux_objeto_desconhecido_p (writer POSTGIS_5)
aux_objeto_desconhecido_p (writer POSTGIS_5) [off]
    attributes: id serial, obs varchar(255)
Counter_2
    CNT_ATTR = _count
    DOMAIN = counter
    SCOPE = Global
    START = 0
    -> Aggregator_2
Aggregator_2
    ACCUM_ATTRS_NAME = Use Attributes From One Feature
    AGGREGATE_TYPE = Homogeneous Collection (If Possible)
    GROUP_BY = _count
    MODE = Geometry - Assemble One Level
    SEP = ,
    AGGREGATE -> aux_objeto_desconhecido_l (writer POSTGIS_5)
aux_objeto_desconhecido_l (writer POSTGIS_5) [off]
    attributes: id serial, obs varchar(255)
Counter_3
    CNT_ATTR = _count
    DOMAIN = counter
    SCOPE = Global
    START = 0
    -> Aggregator_3
Aggregator_3
    ACCUM_ATTRS_NAME = Use Attributes From One Feature
    AGGREGATE_TYPE = Homogeneous Collection (If Possible)
    GROUP_BY = _count
    MODE = Geometry - Assemble One Level
    SEP = ,
    AGGREGATE -> aux_objeto_desconhecido_a (writer POSTGIS_5)
aux_objeto_desconhecido_a (writer POSTGIS_5) [off]
    attributes: id serial, obs varchar(255)
GEOMETRIA_INVALIDA: Inspector
UUIDGenerator
    UUID_ATTR = uid
    -> Tester
Tester
    BOOL_OP = OR
    TEST_CLAUSE = TEST @Value(fme_feature_type) = mgcp.pgb030
    TEST_MODE = TEST
    FAILED -> Table1 (writer POSTGIS_4)
Table1 (writer POSTGIS_4)
