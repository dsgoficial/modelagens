FME workspace conversao_postgis213_shp213_com_recorte_em_lote.fmw

Parameters:
- DestDataset_ESRISHAPE =
- ESPG =
- FEATURE_TYPES_2 =
- HOST_POSTGIS =
- JsonMapeamento =
- PASSWORD_POSTGIS =
- PORT_POSTGIS =
- SourceDataset_ESRISHAPE =
- SourceDataset_POSTGIS =
- SourceDataset_SHAPEFILE =
- USER_NAME_POSTGIS =
- direcao =
- reprojetar =

Readers:
- SHAPEFILE_1: SHAPEFILE from $(SourceDataset_SHAPEFILE)

Note: Molduras
generalizacao_17rcmec_50k (reader SHAPEFILE_1)
    attributes: id long, mi varchar(10), inom varchar(29), escala varchar(254), area_supri varchar(7)
    -> StringSearcher
StringSearcher
    CASE = no
    MATCHED_RESULT_ATTR = _first_match
    REGEXP = 22
    STRING_TO_SEARCH = @Value(inom)
    MATCHED -> Reprojector
Reprojector
    DEST = EPSG:31982
    INTERPOLATION_TYPE_NAME = Nearest Neighbor
    RASTER_CELL_SIZE = Preserve Cells
    RASTER_TOLERANCE = 0.0
    REPROJECTED -> GeometryExtractor
GeometryExtractor
    ATTR = _geometry
    GENERATE_GEOMETRY_IDS = No
    KIND_LONG = OGC Well Known Text
    OGCVERSION = 1.2
    OGC_WKT_PRECISION_DISPLAY = 64-bit
    PREFER_POLYGON_OVER_SURFACE = No
    REMOVE_GEOMETRY = No
    -> AttributeCreator
AttributeCreator
    ATTR_TABLE = SET_TO ewkt = SRID=$(ESPG);@Value(_geometry)
    -> WorkspaceRunner
WorkspaceRunner
    BLOCKING = Yes
    WORKSPACE_FILE = $(FME_MF_DIR)conversao_postgis213_shp213_com_recorte.fmw
    WORKSPACE_PARAMETERS = SourceDataset_POSTGIS,$(SourceDataset_POSTGIS),HOST_POSTGIS,$(HOST_POSTGIS),PORT_POSTGIS,$(PORT_POSTGIS),USER_NAME_POSTGIS,$(USER_NAME_POSTGIS),PASSWORD_POSTGIS,$(PASSWORD_POSTGIS),direcao,$(direcao),JsonMapeamento,$(JsonMapeamento),SourceDataset_ESRISHAPE,$(SourceDataset_ESRISHAPE),DestDataset_ESRISHAPE,$(DestDataset_ESRISHAPE)/@Value(mi),dbarea_where_clause,@Value(ewkt),reprojetar,$(reprojetar)
    SUCCEEDED -> WorkspaceRunner_Succeeded
    FAILED -> WorkspaceRunner_Failed
    SUMMARY -> WorkspaceRunner_Summary
WorkspaceRunner_Succeeded: Inspector
WorkspaceRunner_Failed: Inspector
WorkspaceRunner_Summary: Inspector
