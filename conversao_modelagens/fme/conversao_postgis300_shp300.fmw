FME workspace conversao_postgis300_shp300.fmw

Parameters:
- SourceDataset_POSTGIS = conversao_2cgeo   # Database PG
- HOST_POSTGIS = localhost   # Host PG
- PORT_POSTGIS = 5432   # Port PG
- USER_NAME_POSTGIS = postgres   # Username PG
- PASSWORD_POSTGIS =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   # Password PG
- direcao = ida   # Direção do mapeamento
- JsonMapeamento = C:\Diniz\modelagens\conversao_modelagens\arquivos_mapeamento\conversao_pg-edgv-300_shp-edgv-300.json   # Arquivo de mapeamento
- SourceDataset_ESRISHAPE = ""C:\Diniz\shp300\shp300\AER_Pista_Ponto_Pouso_A.shp" "C:\Diniz\shp300\shp300\AER_Pista_Ponto_Pouso_L.shp" "C:\Diniz\shp300\shp300\AER_Pista_Ponto_Pouso_P.shp" "C:\Diniz\shp300\shp300\CBGE_Area_Agropec_Ext_Vegetal_Pesca_A.shp" "C:\Diniz\shp300\shp300\CBGE_Area_Construida_A.shp" "C:\Diniz\shp300\shp300\CBGE_Area_De_Propriedade_Particular_A.shp" "C:\Diniz\shp300\shp300\CBGE_Area_Duto_A.shp" "C:\Diniz\shp300\shp300\CBGE_Area_Habitacional_A.shp" "C:\Diniz\shp300\shp300\CBGE_Area_Uso_Especifico_A.shp" "C:\Diniz\shp300\shp300\CBGE_Canteiro_Central_A.shp" "C:\Diniz\shp300\shp300\CBGE_Canteiro_Central_L.shp" "C:\Diniz\shp300\shp300\CBGE_Cemiterio_A.shp" "C:\Diniz\shp300\shp300\CBGE_Cemiterio_P.shp" "C:\Diniz\shp300\shp300\CBGE_Delimitacao_Fisica_L.shp" "C:\Diniz\shp300\shp300\CBGE_Deposito_Geral_A.shp" "C:\Diniz\shp300\shp300\CBGE_Deposito_Geral_P.shp" "C:\Diniz\shp300\shp300\CBGE_Entroncamento_Area_A.shp" "C:\Diniz\shp300\shp300\CBGE_Espelho_Dagua_A.shp" "C:\Diniz\shp300\shp300\CBGE_Estacionamento_A.shp" "C:\Diniz\shp300\shp300\CBGE_Largo_A.shp" "C:\Diniz\shp300\shp300\CBGE_Passeio_A.shp" "C:\Diniz\shp300\shp300\CBGE_Passeio_L.shp" "C:\Diniz\shp300\shp300\CBGE_Poste_P.shp" "C:\Diniz\shp300\shp300\CBGE_Praca_A.shp" "C:\Diniz\shp300\shp300\CBGE_Quadra_A.shp" "C:\Diniz\shp300\shp300\CBGE_Retorno_L.shp" "C:\Diniz\shp300\shp300\CBGE_Retorno_P.shp" "C:\Diniz\shp300\shp300\CBGE_Trecho_Arruamento_A.shp" "C:\Diniz\shp300\shp300\CBGE_Trecho_Arruamento_L.shp" "C:\Diniz\shp300\shp300\DUT_Galeria_Bueiro_L.shp" "C:\Diniz\shp300\shp300\DUT_Galeria_Bueiro_P.shp" "C:\Diniz\shp300\shp300\DUT_Trecho_Duto_L.shp" "C:\Diniz\shp300\shp300\ECO_Equip_Agropec_A.shp" "C:\Diniz\shp300\shp300\ECO_Equip_Agropec_L.shp" "C:\Diniz\shp300\shp300\ECO_Equip_Agropec_P.shp" "C:\Diniz\shp300\shp300\ECO_Ext_Mineral_A.shp" "C:\Diniz\shp300\shp300\ECO_Ext_Mineral_P.shp" "C:\Diniz\shp300\shp300\ECO_Plataforma_A.shp" "C:\Diniz\shp300\shp300\ECO_Plataforma_P.shp" "C:\Diniz\shp300\shp300\EDF_Banheiro_Publico_A.shp" "C:\Diniz\shp300\shp300\EDF_Banheiro_Publico_P.shp" "C:\Diniz\shp300\shp300\EDF_Edif_Abast_Agua_A.shp" "C:\Diniz\shp300\shp300\EDF_Edif_Abast_Agua_P.shp" "C:\Diniz\shp300\shp300\EDF_Edif_Agropec_Ext_Vegetal_Pesca_A.shp" "C:\Diniz\shp300\shp300\EDF_Edif_Agropec_Ext_Vegetal_Pesca_P.shp" "C:\Diniz\shp300\shp300\EDF_Edif_Comerc_Serv_A.shp" "C:\Diniz\shp300\shp300\EDF_Edif_Comerc_Serv_P.shp" "C:\Diniz\shp300\shp300\EDF_Edif_Comunic_A.shp" "C:\Diniz\shp300\shp300\EDF_Edif_Comunic_P.shp" "C:\Diniz\shp300\shp300\EDF_Edif_Constr_Aeroportuaria_A.shp" "C:\Diniz\shp300\shp300\EDF_Edif_Constr_Aeroportuaria_P.shp" "C:\Diniz\shp300\shp300\EDF_Edif_Constr_Est_Med_Fen_A.shp" "C:\Diniz\shp300\shp300\EDF_Edif_Constr_Est_Med_Fen_P.shp" "C:\Diniz\shp300\shp300\EDF_Edif_Constr_Lazer_A.shp" "C:\Diniz\shp300\shp300\EDF_Edif_Constr_Lazer_P.shp" "C:\Diniz\shp300\shp300\EDF_Edif_Constr_Portuaria_A.shp" "C:\Diniz\shp300\shp300\EDF_Edif_Constr_Portuaria_P.shp" "C:\Diniz\shp300\shp300\EDF_Edif_Constr_Turistica_A.shp" "C:\Diniz\shp300\shp300\EDF_Edif_Constr_Turistica_P.shp" "C:\Diniz\shp300\shp300\EDF_Edif_Desenv_Social_A.shp" "C:\Diniz\shp300\shp300\EDF_Edif_Desenv_Social_P.shp" "C:\Diniz\shp300\shp300\EDF_Edif_Energia_A.shp" "C:\Diniz\shp300\shp300\EDF_Edif_Energia_P.shp" "C:\Diniz\shp300\shp300\EDF_Edif_Ensino_A.shp" "C:\Diniz\shp300\shp300\EDF_Edif_Ensino_P.shp" "C:\Diniz\shp300\shp300\EDF_Edif_Ext_Mineral_A.shp" "C:\Diniz\shp300\shp300\EDF_Edif_Ext_Mineral_P.shp" "C:\Diniz\shp300\shp300\EDF_Edif_Industrial_A.shp" "C:\Diniz\shp300\shp300\EDF_Edif_Industrial_P.shp" "C:\Diniz\shp300\shp300\EDF_Edif_Metro_Ferroviaria_A.shp" "C:\Diniz\shp300\shp300\EDF_Edif_Metro_Ferroviaria_P.shp" "C:\Diniz\shp300\shp300\EDF_Edif_Policia_A.shp" "C:\Diniz\shp300\shp300\EDF_Edif_Policia_P.shp" "C:\Diniz\shp300\shp300\EDF_Edif_Pub_Civil_A.shp" "C:\Diniz\shp300\shp300\EDF_Edif_Pub_Civil_P.shp" "C:\Diniz\shp300\shp300\EDF_Edif_Pub_Militar_A.shp" "C:\Diniz\shp300\shp300\EDF_Edif_Pub_Militar_P.shp" "C:\Diniz\shp300\shp300\EDF_Edif_Religiosa_A.shp" "C:\Diniz\shp300\shp300\EDF_Edif_Religiosa_P.shp" "C:\Diniz\shp300\shp300\EDF_Edif_Residencial_A.shp" "C:\Diniz\shp300\shp300\EDF_Edif_Residencial_P.shp" "C:\Diniz\shp300\shp300\EDF_Edif_Rodoviaria_A.shp" "C:\Diniz\shp300\shp300\EDF_Edif_Rodoviaria_P.shp" "C:\Diniz\shp300\shp300\EDF_Edif_Saneamento_A.shp" "C:\Diniz\shp300\shp300\EDF_Edif_Saneamento_P.shp" "C:\Diniz\shp300\shp300\EDF_Edif_Saude_A.shp" "C:\Diniz\shp300\shp300\EDF_Edif_Saude_P.shp" "C:\Diniz\shp300\shp300\EDF_Edificacao_A.shp" "C:\Diniz\shp300\shp300\EDF_Edificacao_P.shp" "C:\Diniz\shp300\shp300\EDF_Hab_Indigena_A.shp" "C:\Diniz\shp300\shp300\EDF_Hab_Indigena_P.shp" "C:\Diniz\shp300\shp300\EDF_Posto_Combustivel_A.shp" "C:\Diniz\shp300\shp300\EDF_Posto_Combustivel_P.shp" "C:\Diniz\shp300\shp300\EDF_Posto_Fiscal_A.shp" "C:\Diniz\shp300\shp300\EDF_Posto_Fiscal_P.shp" "C:\Diniz\shp300\shp300\EDF_Posto_Guarda_Municipal_A.shp" "C:\Diniz\shp300\shp300\EDF_Posto_Guarda_Municipal_P.shp" "C:\Diniz\shp300\shp300\EDF_Posto_Policia_Militar_A.shp" "C:\Diniz\shp300\shp300\EDF_Posto_Policia_Militar_P.shp" "C:\Diniz\shp300\shp300\EDF_Posto_Policia_Rod_Federal_A.shp" "C:\Diniz\shp300\shp300\EDF_Posto_Policia_Rod_Federal_P.shp" "C:\Diniz\shp300\shp300\EDF_Representacao_Diplomatica_A.shp" "C:\Diniz\shp300\shp300\EDF_Representacao_Diplomatica_P.shp" "C:\Diniz\shp300\shp300\EMU_Acesso_A.shp" "C:\Diniz\shp300\shp300\EMU_Acesso_L.shp" "C:\Diniz\shp300\shp300\EMU_Acesso_P.shp" "C:\Diniz\shp300\shp300\EMU_Ciclovia_L.shp" "C:\Diniz\shp300\shp300\EMU_Elevador_A.shp" "C:\Diniz\shp300\shp300\EMU_Elevador_L.shp" "C:\Diniz\shp300\shp300\EMU_Elevador_P.shp" "C:\Diniz\shp300\shp300\EMU_Escadaria_A.shp" "C:\Diniz\shp300\shp300\EMU_Escadaria_L.shp" "C:\Diniz\shp300\shp300\EMU_Escadaria_P.shp" "C:\Diniz\shp300\shp300\EMU_Poste_Sinalizacao_P.shp" "C:\Diniz\shp300\shp300\EMU_Rampa_A.shp" "C:\Diniz\shp300\shp300\EMU_Rampa_L.shp" "C:\Diniz\shp300\shp300\EMU_Rampa_P.shp" "C:\Diniz\shp300\shp300\ENC_Aerogerador_P.shp" "C:\Diniz\shp300\shp300\ENC_Antena_Comunic_P.shp" "C:\Diniz\shp300\shp300\ENC_Casa_De_Forca_P.shp" "C:\Diniz\shp300\shp300\ENC_Central_Geradora_Eolica_A.shp" "C:\Diniz\shp300\shp300\ENC_Central_Geradora_Eolica_P.shp" "C:\Diniz\shp300\shp300\ENC_Est_Gerad_Energia_Eletrica_A.shp" "C:\Diniz\shp300\shp300\ENC_Est_Gerad_Energia_Eletrica_P.shp" "C:\Diniz\shp300\shp300\ENC_Grupo_Transformadores_A.shp" "C:\Diniz\shp300\shp300\ENC_Grupo_Transformadores_P.shp" "C:\Diniz\shp300\shp300\ENC_Hidreletrica_A.shp" "C:\Diniz\shp300\shp300\ENC_Hidreletrica_L.shp" "C:\Diniz\shp300\shp300\ENC_Hidreletrica_P.shp" "C:\Diniz\shp300\shp300\ENC_Subest_Transm_Distrib_Energia_Eletrica_A.shp" "C:\Diniz\shp300\shp300\ENC_Termeletrica_A.shp" "C:\Diniz\shp300\shp300\ENC_Termeletrica_P.shp" "C:\Diniz\shp300\shp300\ENC_Torre_Comunic_P.shp" "C:\Diniz\shp300\shp300\ENC_Torre_Energia_P.shp" "C:\Diniz\shp300\shp300\ENC_Trecho_Comunic_L.shp" "C:\Diniz\shp300\shp300\ENC_Trecho_Energia_L.shp" "C:\Diniz\shp300\shp300\ENC_Zona_Linhas_Energia_Comunicacao_A.shp" "C:\Diniz\shp300\shp300\FER_Cremalheira_L.shp" "C:\Diniz\shp300\shp300\FER_Cremalheira_P.shp" "C:\Diniz\shp300\shp300\FER_Girador_Ferroviario_P.shp" "C:\Diniz\shp300\shp300\FER_Trecho_Ferroviario_L.shp" "C:\Diniz\shp300\shp300\HDV_Atracadouro_Terminal_A.shp" "C:\Diniz\shp300\shp300\HDV_Atracadouro_Terminal_L.shp" "C:\Diniz\shp300\shp300\HDV_Atracadouro_Terminal_P.shp" "C:\Diniz\shp300\shp300\HDV_Eclusa_A.shp" "C:\Diniz\shp300\shp300\HDV_Eclusa_L.shp" "C:\Diniz\shp300\shp300\HDV_Eclusa_P.shp" "C:\Diniz\shp300\shp300\HDV_Fundeadouro_A.shp" "C:\Diniz\shp300\shp300\HDV_Fundeadouro_P.shp" "C:\Diniz\shp300\shp300\HDV_Obstaculo_Navegacao_A.shp" "C:\Diniz\shp300\shp300\HDV_Obstaculo_Navegacao_L.shp" "C:\Diniz\shp300\shp300\HDV_Obstaculo_Navegacao_P.shp" "C:\Diniz\shp300\shp300\HDV_Sinalizacao_P.shp" "C:\Diniz\shp300\shp300\HDV_Trecho_Hidroviario_L.shp" "C:\Diniz\shp300\shp300\HID_Area_Umida_A.shp" "C:\Diniz\shp300\shp300\HID_Banco_Areia_A.shp" "C:\Diniz\shp300\shp300\HID_Barragem_A.shp" "C:\Diniz\shp300\shp300\HID_Barragem_L.shp" "C:\Diniz\shp300\shp300\HID_Barragem_P.shp" "C:\Diniz\shp300\shp300\HID_Canal_A.shp" "C:\Diniz\shp300\shp300\HID_Canal_L.shp" "C:\Diniz\shp300\shp300\HID_Comporta_L.shp" "C:\Diniz\shp300\shp300\HID_Comporta_P.shp" "C:\Diniz\shp300\shp300\HID_Corredeira_A.shp" "C:\Diniz\shp300\shp300\HID_Corredeira_L.shp" "C:\Diniz\shp300\shp300\HID_Corredeira_P.shp" "C:\Diniz\shp300\shp300\HID_Dique_A.shp" "C:\Diniz\shp300\shp300\HID_Dique_L.shp" "C:\Diniz\shp300\shp300\HID_Dique_P.shp" "C:\Diniz\shp300\shp300\HID_Fonte_Dagua_P.shp" "C:\Diniz\shp300\shp300\HID_Foz_Maritima_L.shp" "C:\Diniz\shp300\shp300\HID_Foz_Maritima_P.shp" "C:\Diniz\shp300\shp300\HID_Ilha_A.shp" "C:\Diniz\shp300\shp300\HID_Ilha_P.shp" "C:\Diniz\shp300\shp300\HID_Massa_Dagua_A.shp" "C:\Diniz\shp300\shp300\HID_Quebramar_Molhe_A.shp" "C:\Diniz\shp300\shp300\HID_Quebramar_Molhe_L.shp" "C:\Diniz\shp300\shp300\HID_Queda_Dagua_L.shp" "C:\Diniz\shp300\shp300\HID_Queda_Dagua_P.shp" "C:\Diniz\shp300\shp300\HID_Recife_A.shp" "C:\Diniz\shp300\shp300\HID_Recife_P.shp" "C:\Diniz\shp300\shp300\HID_Rocha_Em_Agua_A.shp" "C:\Diniz\shp300\shp300\HID_Rocha_Em_Agua_P.shp" "C:\Diniz\shp300\shp300\HID_Sumidouro_Vertedouro_P.shp" "C:\Diniz\shp300\shp300\HID_Terreno_Sujeito_Inundacao_A.shp" "C:\Diniz\shp300\shp300\HID_Trecho_Drenagem_L.shp" "C:\Diniz\shp300\shp300\HID_Vala_A.shp" "C:\Diniz\shp300\shp300\HID_Vala_L.shp" "C:\Diniz\shp300\shp300\LAZ_Arquibancada_A.shp" "C:\Diniz\shp300\shp300\LAZ_Campo_Quadra_A.shp" "C:\Diniz\shp300\shp300\LAZ_Campo_Quadra_P.shp" "C:\Diniz\shp300\shp300\LAZ_Piscina_A.shp" "C:\Diniz\shp300\shp300\LAZ_Pista_Competicao_A.shp" "C:\Diniz\shp300\shp300\LAZ_Pista_Competicao_L.shp" "C:\Diniz\shp300\shp300\LAZ_Pista_Competicao_P.shp" "C:\Diniz\shp300\shp300\LAZ_Ruina_A.shp" "C:\Diniz\shp300\shp300\LAZ_Ruina_P.shp" "C:\Diniz\shp300\shp300\LAZ_Sitio_Arqueologico_A.shp" "C:\Diniz\shp300\shp300\LAZ_Sitio_Arqueologico_P.shp" "C:\Diniz\shp300\shp300\LML_Area_Densamente_Edificada_A.shp" "C:\Diniz\shp300\shp300\LML_Area_Pub_Militar_A.shp" "C:\Diniz\shp300\shp300\LML_Area_Urbana_Isolada_A.shp" "C:\Diniz\shp300\shp300\LML_Distrito_A.shp" "C:\Diniz\shp300\shp300\LML_Limite_Politico_Administrativo_L.shp" "C:\Diniz\shp300\shp300\LML_Municipio_A.shp" "C:\Diniz\shp300\shp300\LML_Nome_Local_P.shp" "C:\Diniz\shp300\shp300\LML_Pais_A.shp" "C:\Diniz\shp300\shp300\LML_Posic_Geo_Localidade_P.shp" "C:\Diniz\shp300\shp300\LML_Terra_Indigena_A.shp" "C:\Diniz\shp300\shp300\LML_Terra_Publica_A.shp" "C:\Diniz\shp300\shp300\LML_Unidade_Conservacao_A.shp" "C:\Diniz\shp300\shp300\LML_Unidade_Federacao_A.shp" "C:\Diniz\shp300\shp300\LML_Unidade_Protecao_Integral_A.shp" "C:\Diniz\shp300\shp300\LML_Unidade_Uso_Sustentavel_A.shp" "C:\Diniz\shp300\shp300\PTO_Marco_De_Limite_P.shp" "C:\Diniz\shp300\shp300\PTO_Pto_Est_Med_Fenomenos_P.shp" "C:\Diniz\shp300\shp300\PTO_Pto_Geod_Topo_Controle_P.shp" "C:\Diniz\shp300\shp300\PTO_Pto_Ref_Geod_Topo_P.shp" "C:\Diniz\shp300\shp300\REL_Alteracao_Fisiografica_Antropica_A.shp" "C:\Diniz\shp300\shp300\REL_Alteracao_Fisiografica_Antropica_L.shp" "C:\Diniz\shp300\shp300\REL_Alteracao_Fisiografica_Antropica_P.shp" "C:\Diniz\shp300\shp300\REL_Aterro_A.shp" "C:\Diniz\shp300\shp300\REL_Aterro_L.shp" "C:\Diniz\shp300\shp300\REL_Aterro_P.shp" "C:\Diniz\shp300\shp300\REL_Corte_A.shp" "C:\Diniz\shp300\shp300\REL_Corte_L.shp" "C:\Diniz\shp300\shp300\REL_Corte_P.shp" "C:\Diniz\shp300\shp300\REL_Curva_Batimetrica_L.shp" "C:\Diniz\shp300\shp300\REL_Curva_Nivel_L.shp" "C:\Diniz\shp300\shp300\REL_Dolina_A.shp" "C:\Diniz\shp300\shp300\REL_Dolina_P.shp" "C:\Diniz\shp300\shp300\REL_Duna_A.shp" "C:\Diniz\shp300\shp300\REL_Duna_L.shp" "C:\Diniz\shp300\shp300\REL_Duna_P.shp" "C:\Diniz\shp300\shp300\REL_Elemento_Fisiografico_Natural_A.shp" "C:\Diniz\shp300\shp300\REL_Elemento_Fisiografico_Natural_L.shp" "C:\Diniz\shp300\shp300\REL_Elemento_Fisiografico_Natural_P.shp" "C:\Diniz\shp300\shp300\REL_Gruta_Caverna_L.shp" "C:\Diniz\shp300\shp300\REL_Gruta_Caverna_P.shp" "C:\Diniz\shp300\shp300\REL_Pico_P.shp" "C:\Diniz\shp300\shp300\REL_Ponto_Cotado_Altimetrico_P.shp" "C:\Diniz\shp300\shp300\REL_Ponto_Cotado_Batimetrico_P.shp" "C:\Diniz\shp300\shp300\REL_Rocha_A.shp" "C:\Diniz\shp300\shp300\REL_Rocha_L.shp" "C:\Diniz\shp300\shp300\REL_Rocha_P.shp" "C:\Diniz\shp300\shp300\REL_Terreno_Exposto_A.shp" "C:\Diniz\shp300\shp300\ROD_Trecho_Rodoviario_A.shp" "C:\Diniz\shp300\shp300\ROD_Trecho_Rodoviario_L.shp" "C:\Diniz\shp300\shp300\SNB_Barragem_Calcadao_A.shp" "C:\Diniz\shp300\shp300\SNB_Dep_Abast_Agua_A.shp" "C:\Diniz\shp300\shp300\SNB_Dep_Abast_Agua_P.shp" "C:\Diniz\shp300\shp300\TRA_Caminho_Aereo_L.shp" "C:\Diniz\shp300\shp300\TRA_Caminho_Carrocavel_L.shp" "C:\Diniz\shp300\shp300\TRA_Entroncamento_Pto_P.shp" "C:\Diniz\shp300\shp300\TRA_Funicular_L.shp" "C:\Diniz\shp300\shp300\TRA_Passagem_Elevada_Viaduto_A.shp" "C:\Diniz\shp300\shp300\TRA_Passagem_Elevada_Viaduto_L.shp" "C:\Diniz\shp300\shp300\TRA_Passagem_Elevada_Viaduto_P.shp" "C:\Diniz\shp300\shp300\TRA_Passagem_Nivel_P.shp" "C:\Diniz\shp300\shp300\TRA_Patio_A.shp" "C:\Diniz\shp300\shp300\TRA_Ponte_A.shp" "C:\Diniz\shp300\shp300\TRA_Ponte_L.shp" "C:\Diniz\shp300\shp300\TRA_Ponte_P.shp" "C:\Diniz\shp300\shp300\TRA_Travessia_L.shp" "C:\Diniz\shp300\shp300\TRA_Travessia_P.shp" "C:\Diniz\shp300\shp300\TRA_Travessia_Pedestre_A.shp" "C:\Diniz\shp300\shp300\TRA_Travessia_Pedestre_L.shp" "C:\Diniz\shp300\shp300\TRA_Travessia_Pedestre_P.shp" "C:\Diniz\shp300\shp300\TRA_Trilha_Picada_L.shp" "C:\Diniz\shp300\shp300\TRA_Tunel_A.shp" "C:\Diniz\shp300\shp300\TRA_Tunel_L.shp" "C:\Diniz\shp300\shp300\TRA_Tunel_P.shp" "C:\Diniz\shp300\shp300\VEG_Brejo_Pantano_A.shp" "C:\Diniz\shp300\shp300\VEG_Caatinga_A.shp" "C:\Diniz\shp300\shp300\VEG_Campinarana_A.shp" "C:\Diniz\shp300\shp300\VEG_Campo_A.shp" "C:\Diniz\shp300\shp300\VEG_Cerrado_A.shp" "C:\Diniz\shp300\shp300\VEG_Floresta_A.shp" "C:\Diniz\shp300\shp300\VEG_Mangue_A.shp" "C:\Diniz\shp300\shp300\VEG_Reflorestamento_A.shp" "C:\Diniz\shp300\shp300\VEG_Veg_Area_Contato_A.shp" "C:\Diniz\shp300\shp300\VEG_Veg_Cultivada_A.shp" "C:\Diniz\shp300\shp300\VEG_Veg_Restinga_A.shp" "C:\Diniz\shp300\shp300\VER_Arvore_Isolada_P.shp" "C:\Diniz\shp300\shp300\VER_Jardim_A.shp""   # SHPs de referência
- DestDataset_SHAPEFILE = C:\Users\diniz\Downloads\teste   # Destination Esri Shapefile Folder
- FEATURE_TYPES_2 = AER_Pista_Ponto_Pouso_A AER_Pista_Ponto_Pouso_L AER_Pista_Ponto_Pouso_P CBGE_Area_Agropec_Ext_Vegetal_Pesca_A CBGE_Area_Construida_A CBGE_Area_De_Propriedade_Particular_A CBGE_Area_Duto_A CBGE_Area_Habitacional_A CBGE_Area_Uso_Especifico_A CBGE_Canteiro_Central_A CBGE_Canteiro_Central_L CBGE_Cemiterio_A CBGE_Cemiterio_P CBGE_Delimitacao_Fisica_L CBGE_Deposito_Geral_A CBGE_Deposito_Geral_P CBGE_Entroncamento_Area_A CBGE_Espelho_Dagua_A CBGE_Estacionamento_A CBGE_Largo_A CBGE_Passeio_A CBGE_Passeio_L CBGE_Poste_P CBGE_Praca_A CBGE_Quadra_A CBGE_Retorno_L CBGE_Retorno_P CBGE_Trecho_Arruamento_A CBGE_Trecho_Arruamento_L DUT_Galeria_Bueiro_L DUT_Galeria_Bueiro_P DUT_Trecho_Duto_L ECO_Equip_Agropec_A ECO_Equip_Agropec_L ECO_Equip_Agropec_P ECO_Ext_Mineral_A ECO_Ext_Mineral_P ECO_Plataforma_A ECO_Plataforma_P EDF_Banheiro_Publico_A EDF_Banheiro_Publico_P EDF_Edif_Abast_Agua_A EDF_Edif_Abast_Agua_P EDF_Edif_Agropec_Ext_Vegetal_Pesca_A EDF_Edif_Agropec_Ext_Vegetal_Pesca_P EDF_Edif_Comerc_Serv_A EDF_Edif_Comerc_Serv_P EDF_Edif_Comunic_A EDF_Edif_Comunic_P EDF_Edif_Constr_Aeroportuaria_A EDF_Edif_Constr_Aeroportuaria_P EDF_Edif_Constr_Est_Med_Fen_A EDF_Edif_Constr_Est_Med_Fen_P EDF_Edif_Constr_Lazer_A EDF_Edif_Constr_Lazer_P EDF_Edif_Constr_Portuaria_A EDF_Edif_Constr_Portuaria_P EDF_Edif_Constr_Turistica_A EDF_Edif_Constr_Turistica_P EDF_Edif_Desenv_Social_A EDF_Edif_Desenv_Social_P EDF_Edif_Energia_A EDF_Edif_Energia_P EDF_Edif_Ensino_A EDF_Edif_Ensino_P EDF_Edif_Ext_Mineral_A EDF_Edif_Ext_Mineral_P EDF_Edif_Industrial_A EDF_Edif_Industrial_P EDF_Edif_Metro_Ferroviaria_A EDF_Edif_Metro_Ferroviaria_P EDF_Edif_Policia_A EDF_Edif_Policia_P EDF_Edif_Pub_Civil_A EDF_Edif_Pub_Civil_P EDF_Edif_Pub_Militar_A EDF_Edif_Pub_Militar_P EDF_Edif_Religiosa_A EDF_Edif_Religiosa_P EDF_Edif_Residencial_A EDF_Edif_Residencial_P EDF_Edif_Rodoviaria_A EDF_Edif_Rodoviaria_P EDF_Edif_Saneamento_A EDF_Edif_Saneamento_P EDF_Edif_Saude_A EDF_Edif_Saude_P EDF_Edificacao_A EDF_Edificacao_P EDF_Hab_Indigena_A EDF_Hab_Indigena_P EDF_Posto_Combustivel_A EDF_Posto_Combustivel_P EDF_Posto_Fiscal_A EDF_Posto_Fiscal_P EDF_Posto_Guarda_Municipal_A EDF_Posto_Guarda_Municipal_P EDF_Posto_Policia_Militar_A EDF_Posto_Policia_Militar_P EDF_Posto_Policia_Rod_Federal_A EDF_Posto_Policia_Rod_Federal_P EDF_Representacao_Diplomatica_A EDF_Representacao_Diplomatica_P EMU_Acesso_A EMU_Acesso_L EMU_Acesso_P EMU_Ciclovia_L EMU_Elevador_A EMU_Elevador_L EMU_Elevador_P EMU_Escadaria_A EMU_Escadaria_L EMU_Escadaria_P EMU_Poste_Sinalizacao_P EMU_Rampa_A EMU_Rampa_L EMU_Rampa_P ENC_Aerogerador_P ENC_Antena_Comunic_P ENC_Casa_De_Forca_P ENC_Central_Geradora_Eolica_A ENC_Central_Geradora_Eolica_P ENC_Est_Gerad_Energia_Eletrica_A ENC_Est_Gerad_Energia_Eletrica_P ENC_Grupo_Transformadores_A ENC_Grupo_Transformadores_P ENC_Hidreletrica_A ENC_Hidreletrica_L ENC_Hidreletrica_P ENC_Subest_Transm_Distrib_Energia_Eletrica_A ENC_Termeletrica_A ENC_Termeletrica_P ENC_Torre_Comunic_P ENC_Torre_Energia_P ENC_Trecho_Comunic_L ENC_Trecho_Energia_L ENC_Zona_Linhas_Energia_Comunicacao_A FER_Cremalheira_L FER_Cremalheira_P FER_Girador_Ferroviario_P FER_Trecho_Ferroviario_L HDV_Atracadouro_Terminal_A HDV_Atracadouro_Terminal_L HDV_Atracadouro_Terminal_P HDV_Eclusa_A HDV_Eclusa_L HDV_Eclusa_P HDV_Fundeadouro_A HDV_Fundeadouro_P HDV_Obstaculo_Navegacao_A HDV_Obstaculo_Navegacao_L HDV_Obstaculo_Navegacao_P HDV_Sinalizacao_P HDV_Trecho_Hidroviario_L HID_Area_Umida_A HID_Banco_Areia_A HID_Barragem_A HID_Barragem_L HID_Barragem_P HID_Canal_A HID_Canal_L HID_Comporta_L HID_Comporta_P HID_Corredeira_A HID_Corredeira_L HID_Corredeira_P HID_Dique_A HID_Dique_L HID_Dique_P HID_Fonte_Dagua_P HID_Foz_Maritima_L HID_Foz_Maritima_P HID_Ilha_A HID_Ilha_P HID_Massa_Dagua_A HID_Quebramar_Molhe_A HID_Quebramar_Molhe_L HID_Queda_Dagua_L HID_Queda_Dagua_P HID_Recife_A HID_Recife_P HID_Rocha_Em_Agua_A HID_Rocha_Em_Agua_P HID_Sumidouro_Vertedouro_P HID_Terreno_Sujeito_Inundacao_A HID_Trecho_Drenagem_L HID_Vala_A HID_Vala_L LAZ_Arquibancada_A LAZ_Campo_Quadra_A LAZ_Campo_Quadra_P LAZ_Piscina_A LAZ_Pista_Competicao_A LAZ_Pista_Competicao_L LAZ_Pista_Competicao_P LAZ_Ruina_A LAZ_Ruina_P LAZ_Sitio_Arqueologico_A LAZ_Sitio_Arqueologico_P LML_Area_Densamente_Edificada_A LML_Area_Pub_Militar_A LML_Area_Urbana_Isolada_A LML_Distrito_A LML_Municipio_A LML_Nome_Local_P LML_Pais_A LML_Posic_Geo_Localidade_P LML_Terra_Indigena_A LML_Terra_Publica_A LML_Unidade_Conservacao_A LML_Unidade_Federacao_A LML_Unidade_Protecao_Integral_A LML_Unidade_Uso_Sustentavel_A PTO_Marco_De_Limite_P PTO_Pto_Est_Med_Fenomenos_P PTO_Pto_Geod_Topo_Controle_P PTO_Pto_Ref_Geod_Topo_P REL_Alteracao_Fisiografica_Antropica_A REL_Alteracao_Fisiografica_Antropica_L REL_Alteracao_Fisiografica_Antropica_P REL_Aterro_A REL_Aterro_L REL_Aterro_P REL_Corte_A REL_Corte_L REL_Corte_P REL_Curva_Batimetrica_L REL_Curva_Nivel_L REL_Dolina_A REL_Dolina_P REL_Duna_A REL_Duna_L REL_Duna_P REL_Elemento_Fisiografico_Natural_A REL_Elemento_Fisiografico_Natural_L REL_Elemento_Fisiografico_Natural_P REL_Gruta_Caverna_L REL_Gruta_Caverna_P REL_Pico_P REL_Ponto_Cotado_Altimetrico_P REL_Ponto_Cotado_Batimetrico_P REL_Rocha_A REL_Rocha_L REL_Rocha_P REL_Terreno_Exposto_A ROD_Trecho_Rodoviario_A ROD_Trecho_Rodoviario_L SNB_Barragem_Calcadao_A SNB_Dep_Abast_Agua_A SNB_Dep_Abast_Agua_P TRA_Caminho_Aereo_L TRA_Caminho_Carrocavel_L TRA_Entroncamento_Pto_P TRA_Funicular_L TRA_Passagem_Elevada_Viaduto_A TRA_Passagem_Elevada_Viaduto_L TRA_Passagem_Elevada_Viaduto_P TRA_Passagem_Nivel_P TRA_Patio_A TRA_Ponte_A TRA_Ponte_L TRA_Ponte_P TRA_Travessia_L TRA_Travessia_P TRA_Travessia_Pedestre_A TRA_Travessia_Pedestre_L TRA_Travessia_Pedestre_P TRA_Trilha_Picada_L TRA_Tunel_A TRA_Tunel_L TRA_Tunel_P VEG_Brejo_Pantano_A VEG_Caatinga_A VEG_Campinarana_A VEG_Campo_A VEG_Cerrado_A VEG_Floresta_A VEG_Mangue_A VEG_Reflorestamento_A VEG_Veg_Area_Contato_A VEG_Veg_Cultivada_A VEG_Veg_Restinga_A VER_Arvore_Isolada_P VER_Jardim_A
- FEATURE_TYPES = edgv.aer_pista_ponto_pouso_a edgv.aer_pista_ponto_pouso_l edgv.aer_pista_ponto_pouso_p edgv.aux_moldura_a edgv.cbge_area_agropec_ext_vegetal_pesca_a edgv.cbge_area_construida_a edgv.cbge_area_de_propriedade_particular_a edgv.cbge_area_duto_a edgv.cbge_area_habitacional_a edgv.cbge_area_uso_especifico_a edgv.cbge_canteiro_central_a edgv.cbge_canteiro_central_l edgv.cbge_cemiterio_a edgv.cbge_cemiterio_p edgv.cbge_delimitacao_fisica_l edgv.cbge_deposito_geral_a edgv.cbge_deposito_geral_p edgv.cbge_entroncamento_area_a edgv.cbge_espelho_dagua_a edgv.cbge_estacionamento_a edgv.cbge_largo_a edgv.cbge_passeio_a edgv.cbge_passeio_l edgv.cbge_poste_p edgv.cbge_praca_a edgv.cbge_quadra_a edgv.cbge_retorno_l edgv.cbge_retorno_p edgv.cbge_trecho_arruamento_a edgv.cbge_trecho_arruamento_l edgv.dut_galeria_bueiro_l edgv.dut_galeria_bueiro_p edgv.dut_trecho_duto_l edgv.eco_equip_agropec_a edgv.eco_equip_agropec_l edgv.eco_equip_agropec_p edgv.eco_ext_mineral_a edgv.eco_ext_mineral_p edgv.eco_plataforma_a edgv.eco_plataforma_p edgv.edf_banheiro_publico_a edgv.edf_banheiro_publico_p edgv.edf_edif_abast_agua_a edgv.edf_edif_abast_agua_p edgv.edf_edif_agropec_ext_vegetal_pesca_a edgv.edf_edif_agropec_ext_vegetal_pesca_p edgv.edf_edif_comerc_serv_a edgv.edf_edif_comerc_serv_p edgv.edf_edif_comunic_a edgv.edf_edif_comunic_p edgv.edf_edif_constr_aeroportuaria_a edgv.edf_edif_constr_aeroportuaria_p edgv.edf_edif_constr_est_med_fen_a edgv.edf_edif_constr_est_med_fen_p edgv.edf_edif_constr_lazer_a edgv.edf_edif_constr_lazer_p edgv.edf_edif_constr_portuaria_a edgv.edf_edif_constr_portuaria_p edgv.edf_edif_constr_turistica_a edgv.edf_edif_constr_turistica_p edgv.edf_edif_desenv_social_a edgv.edf_edif_desenv_social_p edgv.edf_edif_energia_a edgv.edf_edif_energia_p edgv.edf_edif_ensino_a edgv.edf_edif_ensino_p edgv.edf_edif_ext_mineral_a edgv.edf_edif_ext_mineral_p edgv.edf_edif_industrial_a edgv.edf_edif_industrial_p edgv.edf_edif_metro_ferroviaria_a edgv.edf_edif_metro_ferroviaria_p edgv.edf_edif_policia_a edgv.edf_edif_policia_p edgv.edf_edif_pub_civil_a edgv.edf_edif_pub_civil_p edgv.edf_edif_pub_militar_a edgv.edf_edif_pub_militar_p edgv.edf_edif_religiosa_a edgv.edf_edif_religiosa_p edgv.edf_edif_residencial_a edgv.edf_edif_residencial_p edgv.edf_edif_rodoviaria_a edgv.edf_edif_rodoviaria_p edgv.edf_edif_saneamento_a edgv.edf_edif_saneamento_p edgv.edf_edif_saude_a edgv.edf_edif_saude_p edgv.edf_edificacao_a edgv.edf_edificacao_p edgv.edf_hab_indigena_a edgv.edf_hab_indigena_p edgv.edf_posto_combustivel_a edgv.edf_posto_combustivel_p edgv.edf_posto_fiscal_a edgv.edf_posto_fiscal_p edgv.edf_posto_guarda_municipal_a edgv.edf_posto_guarda_municipal_p edgv.edf_posto_policia_militar_a edgv.edf_posto_policia_militar_p edgv.edf_posto_policia_rod_federal_a edgv.edf_posto_policia_rod_federal_p edgv.edf_representacao_diplomatica_a edgv.edf_representacao_diplomatica_p edgv.emu_acesso_a edgv.emu_acesso_l edgv.emu_acesso_p edgv.emu_ciclovia_l edgv.emu_elevador_a edgv.emu_elevador_l edgv.emu_elevador_p edgv.emu_escadaria_a edgv.emu_escadaria_l edgv.emu_escadaria_p edgv.emu_poste_sinalizacao_p edgv.emu_rampa_a edgv.emu_rampa_l edgv.emu_rampa_p edgv.enc_aerogerador_p edgv.enc_antena_comunic_p edgv.enc_casa_de_forca_p edgv.enc_central_geradora_eolica_a edgv.enc_central_geradora_eolica_p edgv.enc_est_gerad_energia_eletrica_a edgv.enc_est_gerad_energia_eletrica_p edgv.enc_grupo_transformadores_a edgv.enc_grupo_transformadores_p edgv.enc_hidreletrica_a edgv.enc_hidreletrica_l edgv.enc_hidreletrica_p edgv.enc_subest_transm_distrib_energia_eletrica_a edgv.enc_termeletrica_a edgv.enc_termeletrica_p edgv.enc_torre_comunic_p edgv.enc_torre_energia_p edgv.enc_trecho_comunic_l edgv.enc_trecho_energia_l edgv.enc_zona_linhas_energia_comunicacao_a edgv.fer_cremalheira_l edgv.fer_cremalheira_p edgv.fer_girador_ferroviario_p edgv.fer_trecho_ferroviario_l edgv.hdv_atracadouro_terminal_a edgv.hdv_atracadouro_terminal_l edgv.hdv_atracadouro_terminal_p edgv.hdv_eclusa_a edgv.hdv_eclusa_l edgv.hdv_eclusa_p edgv.hdv_fundeadouro_a edgv.hdv_fundeadouro_p edgv.hdv_obstaculo_navegacao_a edgv.hdv_obstaculo_navegacao_l edgv.hdv_obstaculo_navegacao_p edgv.hdv_sinalizacao_p edgv.hdv_trecho_hidroviario_l edgv.hid_area_umida_a edgv.hid_banco_areia_a edgv.hid_barragem_a edgv.hid_barragem_l edgv.hid_barragem_p edgv.hid_canal_a edgv.hid_canal_l edgv.hid_comporta_l edgv.hid_comporta_p edgv.hid_corredeira_a edgv.hid_corredeira_l edgv.hid_corredeira_p edgv.hid_dique_a edgv.hid_dique_l edgv.hid_dique_p edgv.hid_fonte_dagua_p edgv.hid_foz_maritima_l edgv.hid_foz_maritima_p edgv.hid_ilha_a edgv.hid_ilha_p edgv.hid_massa_dagua_a edgv.hid_quebramar_molhe_a edgv.hid_quebramar_molhe_l edgv.hid_queda_dagua_l edgv.hid_queda_dagua_p edgv.hid_recife_a edgv.hid_recife_p edgv.hid_rocha_em_agua_a edgv.hid_rocha_em_agua_p edgv.hid_sumidouro_vertedouro_p edgv.hid_terreno_sujeito_inundacao_a edgv.hid_trecho_drenagem_l edgv.hid_vala_a edgv.hid_vala_l edgv.laz_arquibancada_a edgv.laz_campo_quadra_a edgv.laz_campo_quadra_p edgv.laz_piscina_a edgv.laz_pista_competicao_a edgv.laz_pista_competicao_l edgv.laz_pista_competicao_p edgv.laz_ruina_a edgv.laz_ruina_p edgv.laz_sitio_arqueologico_a edgv.laz_sitio_arqueologico_p edgv.lml_area_densamente_edificada_a edgv.lml_area_pub_militar_a edgv.lml_area_urbana_isolada_a edgv.lml_distrito_a edgv.lml_municipio_a edgv.lml_nome_local_p edgv.lml_pais_a edgv.lml_posic_geo_localidade_p edgv.lml_terra_indigena_a edgv.lml_terra_publica_a edgv.lml_unidade_conservacao_a edgv.lml_unidade_federacao_a edgv.lml_unidade_protecao_integral_a edgv.lml_unidade_uso_sustentavel_a edgv.pto_marco_de_limite_p edgv.pto_pto_est_med_fenomenos_p edgv.pto_pto_geod_topo_controle_p edgv.pto_pto_ref_geod_topo_p edgv.rel_alteracao_fisiografica_antropica_a edgv.rel_alteracao_fisiografica_antropica_l edgv.rel_alteracao_fisiografica_antropica_p edgv.rel_aterro_a edgv.rel_aterro_l edgv.rel_aterro_p edgv.rel_corte_a edgv.rel_corte_l edgv.rel_corte_p edgv.rel_curva_batimetrica_l edgv.rel_curva_nivel_l edgv.rel_dolina_a edgv.rel_dolina_p edgv.rel_duna_a edgv.rel_duna_l edgv.rel_duna_p edgv.rel_elemento_fisiografico_natural_a edgv.rel_elemento_fisiografico_natural_l edgv.rel_elemento_fisiografico_natural_p edgv.rel_gruta_caverna_l edgv.rel_gruta_caverna_p edgv.rel_pico_p edgv.rel_ponto_cotado_altimetrico_p edgv.rel_ponto_cotado_batimetrico_p edgv.rel_rocha_a edgv.rel_rocha_l edgv.rel_rocha_p edgv.rel_terreno_exposto_a edgv.rod_trecho_rodoviario_a edgv.rod_trecho_rodoviario_l edgv.snb_barragem_calcadao_a edgv.snb_dep_abast_agua_a edgv.snb_dep_abast_agua_p edgv.tra_caminho_aereo_l edgv.tra_caminho_carrocavel_l edgv.tra_entroncamento_pto_p edgv.tra_funicular_l edgv.tra_passagem_elevada_viaduto_a edgv.tra_passagem_elevada_viaduto_l edgv.tra_passagem_elevada_viaduto_p edgv.tra_passagem_nivel_p edgv.tra_patio_a edgv.tra_ponte_a edgv.tra_ponte_l edgv.tra_ponte_p edgv.tra_travessia_l edgv.tra_travessia_p edgv.tra_travessia_pedestre_a edgv.tra_travessia_pedestre_l edgv.tra_travessia_pedestre_p edgv.tra_trilha_picada_l edgv.tra_tunel_a edgv.tra_tunel_l edgv.tra_tunel_p edgv.veg_brejo_pantano_a edgv.veg_caatinga_a edgv.veg_campinarana_a edgv.veg_campo_a edgv.veg_cerrado_a edgv.veg_floresta_a edgv.veg_mangue_a edgv.veg_reflorestamento_a edgv.veg_veg_area_contato_a edgv.veg_veg_cultivada_a edgv.veg_veg_restinga_a edgv.ver_arvore_isolada_p edgv.ver_jardim_a

Readers:
- POSTGIS_1: POSTGIS from $(SourceDataset_POSTGIS)
- ESRISHAPE_1: ESRISHAPE from $(SourceDataset_ESRISHAPE)

Writers:
- SHAPEFILE_1: SHAPEFILE to $(DestDataset_SHAPEFILE)

Note: PostGIS EDGV 3.0
adm_area_pub_civil_a (reader POSTGIS_1)
    attributes: id serial, geometriaaproximada int2, tipoedifmil int2, nascente int2, namaximomaximorum int4, obs varchar(255), mattransp int2, tipocemiterio int2, coletiva int2, tipoprodutoresiduo int2, codigootto int4, tipotorre int2, relacionado int2, historicomodificacao varchar(255), classificacaoporte int2, rede int2, tipopostofisc int2, orgaoenteresp varchar(255), potenciafiscalizada float4, perimetrooficial float4, canteirodivisorio int2, tipoobst int2, vaovertical float4, latitude varchar(255), tipoptoestmed int2, tipoptoenergia int2, tipotunel int2, profundidademedia float4, nrdutos int4, denso int2,
      classe varchar(255), pesosuportmaximo float4, especie int2, tiposinal int2, tipotravessia int2, procextracao int2, codigoestacao varchar(255), tipolimpol int2, tipooutlimofic int2, regime int2, nomeabrev varchar(255), referencialaltim int2, tipoedifrod int2, codtrechoferrov varchar(255), tipoestgerad int2, revestimento int2, obssituacao varchar(255), situacaoespacial int2, tipoclassecnae int2, tipomarcolim int2, larguramedia float4, matconstr int2, tipoilha int2, emarruamento int2, dentrodepoligono int2, formaextracao int2, sigla varchar(255), destinadoa int2, caladomax float4, tiporecife int2,
      extensao float4, tipotrechoferrov int2, causa int2, coincidecomdentrode int2, classificacao varchar(255), isolada int2, velocidademedcorrente float4, situacaofisica int2, tipocapital int2, codprojeto varchar(255), espessuradap float4, tipooutunidprot int2, tipoedifagropec int2, destinacaofundeadouro int2, cotacomprovada int2, nrfaixas int4, tipofontedagua int2, especiepredominante int2, arranjofases varchar(255), espessalgas int2, tipodivisaocnae int2, tipogrutacaverna int2, altura float4, nrpistas int4, tipolimareaesp int2, posicaorelativa int2, identificador varchar(255), codestacao varchar(255), tipodepgeral int2, tipolimintramun int2,
      tipousoedif int2, tiporesiduo int2, codponto varchar(255), atolegal varchar(255), periodicidadeinunda varchar(255), tipotravessiaped int2, caladomaxseca float4, destenergelet int2, homologacao int2, datavisita varchar(255), alturalamina float4, tipoassociado int2, cultivopredominante int2, espacamentoindividuos float4, tipoatracad int2, altitudeortometrica float4, gabhorizsup float4, tipocombustivel int2, trafego int2, largura float4, gabvertsup float4, usopista int2, nrlinhas int2, nome varchar(255), extensaotrecho float4, areaoficial varchar(255), modaluso int2, tipopista int2, tipocampo int2, administracao int2,
      tipoaglomrurisol int2, setor int2, posicaopista int2, anocriacao varchar(255), areaoficialha float4, geracao int2, tipousocaminhoaer int2, tipopassagviad int2, tipolavoura int2, alturaestimada float4, compartilhado int2, nivelotto int4, tiporocha int2, tipoponte int2, tipoexposicao int2, codigohidreletrica varchar(255), atividade int2, indice int2, tipotrechoduto int2, navegabilidade int2, tipomacchav int2, numcircuitos int4, tipocaminhoaereo int2, tipocondutor int2, tipoptocontrole int2, situacaoemagua int2, tipotrechocomunic int2, qualidagua int2, tipoedifrelig int2, tipoextmin int2,
      tipodepabast int2, tipolimoper int2, datasituacaojuridica date, tipoedifturist int2, ensino int2, salinidade int2, tipomassadagua int2, materializado int2, tipounidusosust int2, multimodal int2, tipoedifcivil int2, tipoedifaero int2, jurisdicao int2, tipoterrexp int2, emduto int2, tipotrechorod int2, situacaoagua int2, tipoequipagropec int2, funcaoedifmetroferrov int2, outrarefalt varchar(255), vaolivrehoriz float4, tipocampoquadra int2, cargasuportmaxima float4, sistemageodesico int2, cota int4, eletrificada int2, nivelatencao int2, tipoalterantrop int2, tipoplataforma int2, descricao varchar(255),
      unidadevolume int2, mi varchar(255), tensaoeletrica float4, posicaoreledific int2, residuo int2, namaximooperacional int4, alturamediaindividuos float4, tiposumvert int2, finalidade int2, tipoedifabast int2, tiposecaocnae int2, materialpredominante int2, usoprincipal int2, modalidade int2, operacional int2, tipopostopol int2, religiao varchar(255), tipoareausocomun int2, proximidade int2, tipoptorefgeodtopo int2, grupoetnico varchar(255), escala varchar(255), valorvolume float4, situacaocosta int2, geocodigo varchar(255), terreno int2, outrarefplan varchar(255), tipoediflazer int2, causaexposicao int2, chamine int2,
      tipotrechomassa int2, tipoquebramolhe int2, profundidade int4, referencialgrav int2, eixoprincipal int2, tipocerr int2, tipoedifcomunic int2, tipoconteudo int2, potenciaoutorgada float4, nometi varchar(255), tipoareaumida int2, tipobanco int2, ocorrenciaem int2, tipopocomina int2, caracteristicafloresta int2, combrenovavel int2, tipoelemnat int2, tipodelimfis int2, tratamento int2, concessionaria varchar(255), capaccarga float4, anodereferencia int4, codtrechorodov varchar(255), alturamediamargem float4, codiso3166 varchar(255), motivodescontinuidade int2, tipobrejopantano int2, tipoedifsaneam int2, orgresp varchar(255), tipoentroncamento int2,
      tipoedifenergia int2, construcao int2, inom varchar(255), tipomaqtermica int2, denominacaoassociada int2, volumeutil int4, situamare int2, tipoedifcomercserv int2, tipodepsaneam int2, bitola int2, tipolimmassa int2, tipoqueda int2, fixa int2, desnivel float4, situacaomarco int2, tipounidprotinteg int2, calado float4, situacaojuridica int2, ovgd int2, tipolocalcrit int2, longitude varchar(255), depressao int2, tiporef int2, antropizada int2, tipoedifport int2
    -> PythonCaller_2
Note: mapeamento
PythonCaller_2
    NEW_ATTRIBUTES = CLASS_NOT_FOUND
    PYTHONSOURCE:
      import fme
      import fmeobjects
      import copy
      import sys
      import os
      import json

      class FeatureProcessor(object):
          def __init__(self):
              self.mappingDict = self.buildFileDict(FME_MacroValues['JsonMapeamento'])
              self.mappingType = FME_MacroValues['direcao']

          def buildFileDict(self, mappingPath):
              with open(mappingPath, 'r', encoding='utf-8') as file:
                  mapDict = json.loads(file.read())
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          if feature.getAttribute(attr) == 'f':
                              featDict[attr] = 'False'
                          elif feature.getAttribute(attr) == 't':
                              featDict[attr] = 'True'
                          else:
                              featDict[attr] = feature.getAttribute(attr)
                      else:
                          featDict[attr] = None
              if feature.performFunction('@GeometryType()') == 'fme_polygon' or feature.performFunction('@GeometryType()') == 'fme_donut':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              else:
                   featDict["INVALID_GEOM"] = True
              return featDict

          def evaluateExpression(self, featDict, expression):
              if not expression["nome_atributo"] in featDict:
                  return False
              if expression["valor"] is None or expression["valor"] == "":
                  return featDict[expression["nome_atributo"]] is None or featDict[expression["nome_atributo"]] == ""
              else:
                  return u"{0}".format(featDict[expression["nome_atributo"]]) == u"{0}".format(expression["valor"])

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "ida":
                  key_attr_origin = "attr_ida"
                  key_attr_destiny = "attr_volta"
                  key_value_origin = "valor_ida"
                  key_value_destiny = "valor_volta"
                  key_default = "atributos_default_ida"
                  key_filter = "filtro_ida"
                  key_class_origin = "classe_ida"
                  key_class_destiny = "classe_volta"
                  key_group_origin = "tupla_ida"
                  key_group_destiny = "tupla_volta"
                  key_affix_origin = "afixo_geom_ida"
                  key_affix_destiny = "afixo_geom_volta"
                  key_schema_origin = "schema_ida"
                  key_schema_destiny = "schema_volta"
                  key_class_affix_origin = "com_afixo_geom_ida"
                  key_class_affix_destiny = "com_afixo_geom_volta"
                  key_class_schema_origin = "com_schema_ida"
                  key_class_schema_destiny = "com_schema_volta"
                  key_agregar = "agregar_geom_ida"
              else:
                  key_attr_origin = "attr_volta"
                  key_attr_destiny = "attr_ida"
                  key_value_origin = "valor_volta"
                  key_value_destiny = "valor_ida"
                  key_default = "atributos_default_volta"
                  key_filter = "filtro_volta"
                  key_class_origin = "classe_volta"
                  key_class_destiny = "classe_ida"
                  key_group_origin = "tupla_volta"
                  key_group_destiny = "tupla_ida"
                  key_affix_origin = "afixo_geom_volta"
                  key_affix_destiny = "afixo_geom_ida"
                  key_schema_origin = "schema_volta"
                  key_schema_destiny = "schema_ida"
                  key_class_affix_origin = "com_afixo_geom_volta"
                  key_class_affix_destiny = "com_afixo_geom_ida"
                  key_class_schema_origin = "com_schema_volta"
                  key_class_schema_destiny = "com_schema_ida"
                  key_agregar = "agregar_geom_volta"

              featDict["fme_feature_type_original"] = featDict["fme_feature_type"]

              if key_schema_origin in self.mappingDict and self.mappingDict[key_schema_origin]:
                  featDict["fme_feature_type"] = featDict["fme_feature_type"][len(self.mappingDict[key_schema_origin])+1:]

              featDict["fme_feature_type_sem_schema"] = featDict["fme_feature_type"]

              if key_affix_origin in self.mappingDict and 'tipo' in self.mappingDict[key_affix_origin] and self.mappingDict[key_affix_origin]['tipo'] == 'sufixo':
                  featDict["fme_feature_type"] = featDict["fme_feature_type"][:-len(self.mappingDict[key_affix_origin][featDict["$GEOM_TYPE"]])]
                  featDict["fme_feature_type_sem_afixo"] = featDict["fme_feature_type_original"][:-len(self.mappingDict[key_affix_origin][featDict["$GEOM_TYPE"]])]

              if key_affix_origin in self.mappingDict and 'tipo' in self.mappingDict[key_affix_origin] and self.mappingDict[key_affix_origin]['tipo'] == 'prefixo':
                  featDict["fme_feature_type"] = featDict["fme_feature_type"][len(self.mappingDict[key_affix_origin][featDict["$GEOM_TYPE"]]):]
                  featDict["fme_feature_type_sem_afixo"] = featDict["fme_feature_type_original"][len(self.mappingDict[key_affix_origin][featDict["$GEOM_TYPE"]]):]

              should_map = False
              for classmap in self.mappingDict['mapeamento_classes']:
                  if "sentido" not in classmap or ("sentido" in classmap and classmap["sentido"] == self.mappingType):
                      if key_class_affix_origin in classmap and classmap[key_class_affix_origin] and key_class_schema_origin in classmap and classmap[key_class_schema_origin]:
                          class_name = featDict["fme_feature_type_original"]
                      elif key_class_affix_origin in classmap and classmap[key_class_affix_origin]:
                          class_name = featDict["fme_feature_type_sem_schema"]
                      elif key_class_schema_origin in classmap and classmap[key_class_schema_origin]:
                          class_name = featDict["fme_feature_type_sem_afixo"]
                      else:
                           class_name = featDict["fme_feature_type"]

                      if classmap[key_class_origin] == class_name:
                          if key_filter in classmap:
                              if not self.evaluateFilter(featDict, classmap[key_filter]):
                                  continue
                          should_map = True
              if not should_map:
                  featDict["CLASS_NOT_FOUND"] = True
                  return featDict

              mappedFeat = copy.deepcopy(featDict)

              if key_default in self.mappingDict:
                  for default in self.mappingDict[key_default]:
                      mappedFeat[default["nome_atributo"]] = default["valor"]

              if 'mapeamento_atributos' in self.mappingDict:
                  for attmap in self.mappingDict['mapeamento_atributos']:
                      if attmap[key_attr_origin] in mappedFeat:
                          mappedFeat[attmap[key_attr_destiny]] = featDict[attmap[key_attr_origin]]
                          if "traducao" in attmap:
                              for valuemap in attmap["traducao"]:
                                  if u"{0}".format(valuemap[key_value_origin]) == u"{0}".format(featDict[attmap[key_attr_origin]]) and ("sentido" not in valuemap or ("sentido" in valuemap and valuemap["sentido"] == self.mappingType)):
                                      mappedFeat[attmap[key_attr_destiny]] = valuemap[key_value_destiny]

              if "mapeamento_multiplo" in self.mappingDict:
                  for attmap in self.mappingDict['mapeamento_multiplo']:
                      if "sentido" not in attmap or ("sentido" in attmap and attmap["sentido"] == self.mappingType):
                          if all([self.evaluateExpression(featDict, condition) for condition in attmap[key_group_origin]]):
                              for valuemap in attmap[key_group_destiny]:
                                  if "concatenar" in valuemap and valuemap["concatenar"] and valuemap["nome_atributo"] in mappedFeat and mappedFeat[valuemap["nome_atributo"]]:
                                      mappedFeat[valuemap["nome_atributo"]] = mappedFeat[valuemap["nome_atributo"]] + ' | ' + valuemap["valor"]
                                  else:
                                      mappedFeat[valuemap["nome_atributo"]] = valuemap["valor"]

              if 'mapeamento_classes' in self.mappingDict:
                  for classmap in self.mappingDict['mapeamento_classes']:
                      if "sentido" not in classmap or ("sentido" in classmap and classmap["sentido"] == self.mappingType):
                          if key_class_affix_origin in classmap and classmap[key_class_affix_origin] and key_class_schema_origin in classmap and classmap[key_class_schema_origin]:
                              class_name = featDict["fme_feature_type_original"]
                          elif key_class_affix_origin in classmap and classmap[key_class_affix_origin]:
                              class_name = featDict["fme_feature_type_sem_schema"]
                          elif key_class_schema_origin in classmap and classmap[key_class_schema_origin]:
                              class_name = featDict["fme_feature_type_sem_afixo"]
                          else:
                              class_name = featDict["fme_feature_type"]

                          if classmap[key_class_origin] == class_name:
                              if key_filter in classmap:
                                  if not self.evaluateFilter(featDict, classmap[key_filter]):
                                      continue

                              mappedFeat["fme_feature_type"] = classmap[key_class_destiny]

                              if key_class_affix_destiny in classmap and classmap[key_class_affix_destiny]:
                                  pass
                              elif key_affix_destiny in self.mappingDict and 'tipo' in self.mappingDict[key_affix_destiny]:
                                  if self.mappingDict[key_affix_destiny]['tipo'] == 'sufixo':
                                      mappedFeat["fme_feature_type"] = mappedFeat["fme_feature_type"] + self.mappingDict[key_affix_destiny][featDict["$GEOM_TYPE"]]

                                  if self.mappingDict[key_affix_destiny]['tipo'] == 'prefixo':
                                      mappedFeat["fme_feature_type"] = self.mappingDict[key_affix_destiny][featDict["$GEOM_TYPE"]] + mappedFeat["fme_feature_type"]

                              if key_class_schema_destiny in classmap and classmap[key_class_schema_destiny]:
                                  pass
                              elif key_schema_destiny in self.mappingDict and self.mappingDict[key_schema_destiny]:
                                  mappedFeat["fme_feature_type"] = self.mappingDict[key_schema_destiny] + '.' + mappedFeat["fme_feature_type"]


                              if key_default in classmap:
                                  for default in classmap[key_default]:
                                      mappedFeat[default["nome_atributo"]] = default["valor"]

                              if "mapeamento_atributos" in classmap:
                                  for attmap in classmap['mapeamento_atributos']:
                                      if attmap[key_attr_origin] in featDict:
                                          if attmap[key_attr_destiny] not in mappedFeat:
                                              mappedFeat[attmap[key_attr_destiny]] = featDict[attmap[key_attr_origin]]
                                          if "traducao" in attmap:
                                              for valuemap in attmap["traducao"]:
                                                  if u"{0}".format(valuemap[key_value_origin]) == u"{0}".format(featDict[attmap[key_attr_origin]]) and ("sentido" not in valuemap or ("sentido" in valuemap and valuemap["sentido"] == self.mappingType)):
                                                      mappedFeat[attmap[key_attr_destiny]] = valuemap[key_value_destiny]

                              if "mapeamento_multiplo" in classmap:
                                  for attmap in classmap['mapeamento_multiplo']:
                                      if "sentido" not in attmap or ("sentido" in attmap and attmap["sentido"] == self.mappingType):
                                          if all([self.evaluateExpression(featDict, condition) for condition in attmap[key_group_origin]]):
                                              for valuemap in attmap[key_group_destiny]:
                                                  if "concatenar" in valuemap and valuemap["concatenar"] and valuemap["nome_atributo"] in mappedFeat and mappedFeat[valuemap["nome_atributo"]]:
                                                      mappedFeat[valuemap["nome_atributo"]] = mappedFeat[valuemap["nome_atributo"]] + ' | ' + valuemap["valor"]
                                                  else:
                                                      mappedFeat[valuemap["nome_atributo"]] = valuemap["valor"]

                              if key_agregar in classmap:
                                  mappedFeat["AGGREGATE_GEOM"] = classmap[key_agregar]
                              elif key_agregar in self.mappingDict:
                                  mappedFeat["AGGREGATE_GEOM"] = self.mappingDict[key_agregar]

                              break

              return mappedFeat

          def mapDictToFeature(self, feat, featDict):
              for attr, value in featDict.items():
                  if value or value == 0:
                      feat.setAttribute(attr, u'{0}'.format(value))
                  else:
                      feat.setAttributeNullWithType(attr,0)
              if "AGGREGATE_GEOM" in featDict and featDict["AGGREGATE_GEOM"]:
                  feat.buildAggregateFeat([feat])
              return feat

          def input(self,feature):
              if feature.performFunction('@GeometryType()') == 'fme_aggregate':
                  features = feature.splitAggregate(True)
              else:
                  features = [feature]
              for simple_feature in features:
                  feat = self.buildFeatureDict(simple_feature)
                  if "INVALID_GEOM" in feat and not feat["INVALID_GEOM"]:
                      simple_feature.setAttribute("INVALID_GEOM", u'True')
                      self.pyoutput(simple_feature)
                      continue

                  outputFeatDict = self.convertFeature(feat)
                  if "CLASS_NOT_FOUND" in outputFeatDict and not outputFeatDict["CLASS_NOT_FOUND"]:
                      simple_feature.setAttribute("CLASS_NOT_FOUND", u'True')
                      self.pyoutput(simple_feature)
                  else:
                      outputFeature = self.mapDictToFeature(simple_feature, outputFeatDict)
                      self.pyoutput(outputFeature)

          def close(self):
              pass
    PYTHONSYMBOL = FeatureProcessor
    -> Tester_4
Note: Teste de mapeamento
Tester_4
    BOOL_OP = OR
    TEST_CLAUSE = TEST @Value(CLASS_NOT_FOUND) = True
    TEST_MODE = TEST
    PASSED -> CLASSE_NAO_ENCONTRADA
    FAILED -> Counter
CLASSE_NAO_ENCONTRADA: Inspector [off]
Counter
    CNT_ATTR = ID
    DOMAIN = @Value(fme_feature_type)
    SCOPE = Global
    START = 1
    -> cb.adm_area_pub_civil_a (writer SHAPEFILE_1)
cb.adm_area_pub_civil_a (writer SHAPEFILE_1)
    attributes: id long, geometriaa short, tipoedifmi short, nascente short, namaximoma long, obs varchar(255), mattransp short, tipocemite short, coletiva short, tipoprodut short, codigootto long, tipotorre short, relacionad short, historicom varchar(255), classifica short, rede short, tipopostof short, orgaoenter varchar(255), potenciafi float, perimetroo float, canteirodi short, tipoobst short, vaovertica float, latitude varchar(255), tipoptoest short, tipoptoene short, tipotunel short, profundida float, nrdutos long, denso short,
      classe varchar(255), pesosuport float, especie short, tiposinal short, tipotraves short, procextrac short, codigoesta varchar(255), tipolimpol short, tipooutlim short, regime short, nomeabrev varchar(255), referencia short, tipoedifro short, codtrechof varchar(255), tipoestger short, revestimen short, obssituaca varchar(255), situacaoes short, tipoclasse short, tipomarcol short, larguramed float, matconstr short, tipoilha short, emarruamen short, dentrodepo short, formaextra short, sigla varchar(255), destinadoa short, caladomax float, tiporecife short,
      extensao float, tipotrecho short, causa short, coincideco short, classifi00 varchar(255), isolada short, velocidade float, situacaofi short, tipocapita short, codprojeto varchar(255), espessurad float, tipooutuni short, tipoedifag short, destinacao short, cotacompro short, nrfaixas long, tipofonted short, especiepre short, arranjofas varchar(255), espessalga short, tipodivisa short, tipogrutac short, altura float, nrpistas long, tipolimare short, posicaorel short, identifica varchar(255), codestacao varchar(255), tipodepger short, tipolimint short,
      tipousoedi short, tiporesidu short, codponto varchar(255), atolegal varchar(255), periodicid varchar(255), tipotrav00 short, caladomaxs float, destenerge short, homologaca short, datavisita varchar(255), alturalami float, tipoassoci short, cultivopre short, espacament float, tipoatraca short, altitudeor float, gabhorizsu float, tipocombus short, trafego short, largura float, gabvertsup float, usopista short, nrlinhas short, nome varchar(255), extensaotr float, areaoficia varchar(255), modaluso short, tipopista short, tipocampo short, administra short,
      tipoaglomr short, setor short, posicaopis short, anocriacao varchar(255), areaofic00 float, geracao short, tipousocam short, tipopassag short, tipolavour short, alturaesti float, compartilh short, nivelotto long, tiporocha short, tipoponte short, tipoexposi short, codigohidr varchar(255), atividade short, indice short, tipotrec00 short, navegabili short, tipomaccha short, numcircuit long, tipocaminh short, tipocondut short, tipoptocon short, situacaoem short, tipotrec01 short, qualidagua short, tipoedifre short, tipoextmin short,
      tipodepaba short, tipolimope short, datasituac date, tipoediftu short, ensino short, salinidade short, tipomassad short, materializ short, tipounidus short, multimodal short, tipoedifci short, tipoedifae short, jurisdicao short, tipoterrex short, emduto short, tipotrec02 short, situacaoag short, tipoequipa short, funcaoedif short, outrarefal varchar(255), vaolivreho float, tipocampoq short, cargasupor float, sistemageo short, cota long, eletrifica short, nivelatenc short, tipoaltera short, tipoplataf short, descricao varchar(255),
      unidadevol short, mi varchar(255), tensaoelet float, posicaor00 short, residuo short, namaximoop long, alturamedi float, tiposumver short, finalidade short, tipoedifab short, tiposecaoc short, materialpr short, usoprincip short, modalidade short, operaciona short, tipopostop short, religiao varchar(255), tipoareaus short, proximidad short, tipoptoref short, grupoetnic varchar(255), escala varchar(255), valorvolum float, situacaoco short, geocodigo varchar(255), terreno short, outrarefpl varchar(255), tipoedifla short, causaexpos short, chamine short,
      tipotrec03 short, tipoquebra short, profundi00 long, referenc00 short, eixoprinci short, tipocerr short, tipoedifco short, tipoconteu short, potenciaou float, nometi varchar(255), tipoareaum short, tipobanco short, ocorrencia short, tipopocomi short, caracteris short, combrenova short, tipoelemna short, tipodelimf short, tratamento short, concession varchar(255), capaccarga float, anoderefer long, codtrechor varchar(255), alturame00 float, codiso3166 varchar(255), motivodesc short, tipobrejop short, tipoedifsa short, orgresp varchar(255), tipoentron short,
      tipoedifen short, construcao short, inom varchar(255), tipomaqter short, denominaca short, volumeutil long, situamare short, tipoedif00 short, tipodepsan short, bitola short, tipolimmas short, tipoqueda short, fixa short, desnivel float, situacaoma short, tipounidpr short, calado float, situacaoju short, ovgd short, tipolocalc short, longitude varchar(255), depressao short, tiporef short, antropizad short, tipoedifpo short, fme_featur varchar(50)
Note: SHP EDGV 3.0 / utilizado como recurso pro mapeamento dinâmico
ADM_Area_Pub_Civil_A (reader ESRISHAPE_1) [off]
    attributes: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
