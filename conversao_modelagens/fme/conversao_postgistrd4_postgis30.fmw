FME workspace conversao_postgistrd4_postgis30.fmw

Parameters:
- direcao = A=>B   # Direção do mapeamento
- JsonMapeamento = C:\Diniz\modelagens\modelagens_legadas\conversao_modelagens\conversao_pg-trd-44_pg-edgv-300.json   # Arquivo de mapeamento TRD->EDGV3
- FEATURE_TYPES = mgcp.aa010_a mgcp.aa010_p mgcp.aa012_a mgcp.aa012_p mgcp.aa040_p mgcp.aa050_p mgcp.aa052_a mgcp.ab000_a mgcp.ab010_a mgcp.ac000_a mgcp.ac000_p mgcp.ac020_p mgcp.ac030_a mgcp.ac030_p mgcp.ad010_a mgcp.ad010_p mgcp.ad020_p mgcp.ad030_a mgcp.ad030_p mgcp.ad050_a mgcp.ad050_p mgcp.af010_p mgcp.af020_l mgcp.af040_p mgcp.af070_p mgcp.ah025_l mgcp.ah050_a mgcp.ah050_p mgcp.ah070_p mgcp.ai030_a mgcp.aj010_a mgcp.aj030_a mgcp.aj030_p mgcp.aj050_p mgcp.aj051_p mgcp.aj110_a mgcp.aj110_p mgcp.ak030_a mgcp.ak040_a mgcp.ak040_p mgcp.ak060_a mgcp.ak090_a mgcp.ak100_a mgcp.ak120_a mgcp.ak130_l mgcp.ak150_l mgcp.ak150_p mgcp.ak160_a mgcp.ak160_p mgcp.ak170_a mgcp.ak170_p mgcp.ak180_a mgcp.ak190_a mgcp.ak190_l mgcp.al010_a mgcp.al012_a mgcp.al012_p mgcp.al015_a mgcp.al015_p mgcp.al019_a mgcp.al019_p mgcp.al020_a mgcp.al020_p mgcp.al025_p mgcp.al030_a mgcp.al030_p mgcp.al060_a mgcp.al060_l mgcp.al070_l mgcp.al099_p mgcp.al105_a mgcp.al105_p mgcp.al130_p mgcp.al140_a mgcp.al170_a mgcp.al200_a mgcp.al208_a mgcp.al210_l mgcp.al210_p mgcp.al241_p mgcp.al260_l mgcp.am010_a mgcp.am020_a mgcp.am020_p mgcp.am030_a mgcp.am030_p mgcp.am040_a mgcp.am040_p mgcp.am060_a mgcp.am060_p mgcp.am070_a mgcp.am070_p mgcp.an010_l mgcp.an050_l mgcp.an060_a mgcp.an075_p mgcp.an076_a mgcp.an076_p mgcp.ap010_l mgcp.ap030_l mgcp.ap050_l mgcp.aq040_a mgcp.aq040_l mgcp.aq063_l mgcp.aq065_p mgcp.aq070_l mgcp.aq070_p mgcp.aq075_l mgcp.aq090_p mgcp.aq110_p mgcp.aq113_l mgcp.aq116_a mgcp.aq116_p mgcp.aq125_a mgcp.aq125_p mgcp.aq130_a mgcp.aq130_l mgcp.aq135_a mgcp.aq140_a mgcp.at010_p mgcp.at030_l mgcp.at041_l mgcp.at042_p mgcp.at045_p mgcp.at050_a mgcp.at060_l mgcp.aux_moldura_a mgcp.aux_observacao_a mgcp.aux_observacao_l mgcp.aux_observacao_p mgcp.aux_revisao_a mgcp.aux_revisao_l mgcp.aux_revisao_p mgcp.aux_validacao_a mgcp.aux_validacao_l mgcp.aux_validacao_p mgcp.ba010_l mgcp.ba030_a mgcp.ba040_a mgcp.ba050_a mgcp.ba050_p mgcp.bb005_a mgcp.bb041_a mgcp.bb041_l mgcp.bb043_a mgcp.bb043_l mgcp.bb090_a mgcp.bb140_a mgcp.bb140_l mgcp.bb155_p mgcp.bb190_a mgcp.bb190_l mgcp.bb230_l mgcp.bb240_a mgcp.bd100_a mgcp.bd100_p mgcp.bd110_p mgcp.bd120_a mgcp.bd120_l mgcp.bd130_p mgcp.bd180_p mgcp.bh010_a mgcp.bh010_l mgcp.bh010_p mgcp.bh015_a mgcp.bh020_a mgcp.bh020_l mgcp.bh030_a mgcp.bh030_l mgcp.bh040_a mgcp.bh050_a mgcp.bh051_a mgcp.bh060_l mgcp.bh070_l mgcp.bh070_p mgcp.bh080_a mgcp.bh090_a mgcp.bh110_l mgcp.bh120_a mgcp.bh120_l mgcp.bh120_p mgcp.bh130_a mgcp.bh135_a mgcp.bh140_a mgcp.bh140_l mgcp.bh145_p mgcp.bh150_a mgcp.bh155_a mgcp.bh160_a mgcp.bh165_a mgcp.bh165_l mgcp.bh170_p mgcp.bh180_l mgcp.bh180_p mgcp.bi010_p mgcp.bi020_a mgcp.bi020_l mgcp.bi020_p mgcp.bi030_a mgcp.bi030_l mgcp.bi030_p mgcp.bi040_l mgcp.bi040_p mgcp.bi041_l mgcp.bi041_p mgcp.bi050_p mgcp.bj020_a mgcp.bj030_a mgcp.bj031_a mgcp.bj031_l mgcp.bj040_l mgcp.bj060_p mgcp.bj100_a mgcp.bj110_a mgcp.centroide_aa010_p mgcp.centroide_aa012_p mgcp.centroide_al020_p mgcp.centroide_ba030_p mgcp.centroide_ba040_p mgcp.centroide_bh010_p mgcp.centroide_bh015_p mgcp.centroide_bh020_p mgcp.centroide_bh030_p mgcp.centroide_bh080_p mgcp.centroide_bh090_p mgcp.centroide_bh120_p mgcp.centroide_bh130_p mgcp.centroide_bh135_p mgcp.centroide_bh140_p mgcp.centroide_bh150_p mgcp.centroide_bh160_p mgcp.centroide_bj020_p mgcp.centroide_bj030_p mgcp.centroide_bj100_p mgcp.centroide_bj110_p mgcp.centroide_da010_p mgcp.centroide_db170_p mgcp.centroide_ea010_p mgcp.centroide_ea040_p mgcp.centroide_ea050_p mgcp.centroide_ea055_p mgcp.centroide_eb010_p mgcp.centroide_eb020_p mgcp.centroide_ec010_p mgcp.centroide_ec030_p mgcp.centroide_ec040_p mgcp.centroide_ed010_p mgcp.centroide_ed020_p mgcp.centroide_ed030_p mgcp.centroide_zd020_p mgcp.da010_a mgcp.db010_l mgcp.db029_p mgcp.db061_a mgcp.db061_l mgcp.db070_l mgcp.db071_l mgcp.db090_a mgcp.db090_l mgcp.db100_l mgcp.db110_l mgcp.db115_a mgcp.db115_p mgcp.db150_p mgcp.db160_a mgcp.db160_l mgcp.db160_p mgcp.db170_a mgcp.db180_a mgcp.db180_p mgcp.db200_a mgcp.db200_l mgcp.delimitador_area_edificada_l mgcp.delimitador_area_sem_dados_l mgcp.delimitador_cobertura_do_solo_l mgcp.delimitador_elemento_hidrografico_l mgcp.delimitador_massa_dagua_l mgcp.ea010_a mgcp.ea020_l mgcp.ea040_a mgcp.ea050_a mgcp.ea055_a mgcp.eb010_a mgcp.eb020_a mgcp.ec010_a mgcp.ec020_a mgcp.ec030_a mgcp.ec030_l mgcp.ec030_p mgcp.ec040_a mgcp.ec060_a mgcp.ed010_a mgcp.ed020_a mgcp.ed030_a mgcp.fa015_a mgcp.fa090_l mgcp.fa100_a mgcp.ga034_p mgcp.gb005_a mgcp.gb015_a mgcp.gb030_p mgcp.gb035_a mgcp.gb040_p mgcp.gb045_a mgcp.gb050_l mgcp.gb050_p mgcp.gb055_a mgcp.gb065_a mgcp.gb065_p mgcp.gb075_a mgcp.gb220_p mgcp.gb230_a mgcp.gb230_p mgcp.gb485_p mgcp.su001_a mgcp.su001_p mgcp.zd020_a mgcp.zd040_p
- SourceDataset_POSTGIS_2 = w055s26   # Database
- postgis_sql_where_clause =
- DestDataset_POSTGIS = w055s26_edgv30   # Database
- SourceDataset_POSTGIS = w055s26_edgv30   # Database
- FEATURE_TYPES_2 = edgv.aer_pista_ponto_pouso_a edgv.aer_pista_ponto_pouso_l edgv.aer_pista_ponto_pouso_p edgv.aux_moldura_a edgv.aux_obstaculo_vertical_p edgv.aux_revisao_a edgv.aux_revisao_l edgv.aux_revisao_p edgv.cbge_area_agropec_ext_vegetal_pesca_a edgv.cbge_area_construida_a edgv.cbge_area_de_propriedade_particular_a edgv.cbge_area_duto_a edgv.cbge_area_habitacional_a edgv.cbge_area_uso_especifico_a edgv.cbge_assentamento_precario_a edgv.cbge_canteiro_central_a edgv.cbge_canteiro_central_l edgv.cbge_cemiterio_a edgv.cbge_cemiterio_p edgv.cbge_delimitacao_fisica_l edgv.cbge_deposito_geral_a edgv.cbge_deposito_geral_p edgv.cbge_entroncamento_area_a edgv.cbge_espelho_dagua_a edgv.cbge_estacionamento_a edgv.cbge_largo_a edgv.cbge_passeio_a edgv.cbge_passeio_l edgv.cbge_poste_p edgv.cbge_praca_a edgv.cbge_quadra_a edgv.cbge_retorno_l edgv.cbge_retorno_p edgv.cbge_trecho_arruamento_a edgv.cbge_trecho_arruamento_l edgv.dut_galeria_bueiro_l edgv.dut_galeria_bueiro_p edgv.dut_trecho_duto_l edgv.eco_equip_agropec_a edgv.eco_equip_agropec_l edgv.eco_equip_agropec_p edgv.eco_ext_mineral_a edgv.eco_ext_mineral_p edgv.eco_plataforma_a edgv.eco_plataforma_p edgv.edf_banheiro_publico_a edgv.edf_banheiro_publico_p edgv.edf_edif_abast_agua_a edgv.edf_edif_abast_agua_p edgv.edf_edif_agropec_ext_vegetal_pesca_a edgv.edf_edif_agropec_ext_vegetal_pesca_p edgv.edf_edif_comerc_serv_a edgv.edf_edif_comerc_serv_p edgv.edf_edif_comunic_a edgv.edf_edif_comunic_p edgv.edf_edif_constr_aeroportuaria_a edgv.edf_edif_constr_aeroportuaria_p edgv.edf_edif_constr_est_med_fen_a edgv.edf_edif_constr_est_med_fen_p edgv.edf_edif_constr_lazer_a edgv.edf_edif_constr_lazer_p edgv.edf_edif_constr_portuaria_a edgv.edf_edif_constr_portuaria_p edgv.edf_edif_constr_turistica_a edgv.edf_edif_constr_turistica_p edgv.edf_edif_desenv_social_a edgv.edf_edif_desenv_social_p edgv.edf_edif_energia_a edgv.edf_edif_energia_p edgv.edf_edif_ensino_a edgv.edf_edif_ensino_p edgv.edf_edif_ext_mineral_a edgv.edf_edif_ext_mineral_p edgv.edf_edif_industrial_a edgv.edf_edif_industrial_p edgv.edf_edif_metro_ferroviaria_a edgv.edf_edif_metro_ferroviaria_p edgv.edf_edif_policia_a edgv.edf_edif_policia_p edgv.edf_edif_pub_civil_a edgv.edf_edif_pub_civil_p edgv.edf_edif_pub_militar_a edgv.edf_edif_pub_militar_p edgv.edf_edif_religiosa_a edgv.edf_edif_religiosa_p edgv.edf_edif_residencial_a edgv.edf_edif_residencial_p edgv.edf_edif_rodoviaria_a edgv.edf_edif_rodoviaria_p edgv.edf_edif_saneamento_a edgv.edf_edif_saneamento_p edgv.edf_edif_saude_a edgv.edf_edif_saude_p edgv.edf_edificacao_a edgv.edf_edificacao_p edgv.edf_hab_indigena_a edgv.edf_hab_indigena_p edgv.edf_posto_combustivel_a edgv.edf_posto_combustivel_p edgv.edf_posto_fiscal_a edgv.edf_posto_fiscal_p edgv.edf_posto_guarda_municipal_a edgv.edf_posto_guarda_municipal_p edgv.edf_posto_policia_militar_a edgv.edf_posto_policia_militar_p edgv.edf_posto_policia_rod_federal_a edgv.edf_posto_policia_rod_federal_p edgv.edf_representacao_diplomatica_a edgv.edf_representacao_diplomatica_p edgv.emu_acesso_a edgv.emu_acesso_l edgv.emu_acesso_p edgv.emu_ciclovia_l edgv.emu_elevador_a edgv.emu_elevador_l edgv.emu_elevador_p edgv.emu_escadaria_a edgv.emu_escadaria_l edgv.emu_escadaria_p edgv.emu_poste_sinalizacao_p edgv.emu_rampa_a edgv.emu_rampa_l edgv.emu_rampa_p edgv.enc_aerogerador_p edgv.enc_antena_comunic_p edgv.enc_casa_de_forca_p edgv.enc_central_geradora_eolica_a edgv.enc_central_geradora_eolica_l edgv.enc_central_geradora_eolica_p edgv.enc_est_gerad_energia_eletrica_a edgv.enc_est_gerad_energia_eletrica_l edgv.enc_est_gerad_energia_eletrica_p edgv.enc_grupo_transformadores_a edgv.enc_grupo_transformadores_p edgv.enc_hidreletrica_a edgv.enc_hidreletrica_l edgv.enc_hidreletrica_p edgv.enc_subest_transm_distrib_energia_eletrica_a edgv.enc_subest_transm_distrib_energia_eletrica_p edgv.enc_termeletrica_a edgv.enc_termeletrica_p edgv.enc_torre_comunic_p edgv.enc_torre_energia_p edgv.enc_trecho_comunic_l edgv.enc_trecho_energia_l edgv.enc_zona_linhas_energia_comunicacao_a edgv.fer_cremalheira_l edgv.fer_cremalheira_p edgv.fer_girador_ferroviario_p edgv.fer_trecho_ferroviario_l edgv.hdv_atracadouro_terminal_a edgv.hdv_atracadouro_terminal_l edgv.hdv_atracadouro_terminal_p edgv.hdv_eclusa_a edgv.hdv_eclusa_l edgv.hdv_eclusa_p edgv.hdv_fundeadouro_a edgv.hdv_fundeadouro_p edgv.hdv_obstaculo_navegacao_a edgv.hdv_obstaculo_navegacao_l edgv.hdv_obstaculo_navegacao_p edgv.hdv_sinalizacao_p edgv.hdv_trecho_hidroviario_l edgv.hid_area_umida_a edgv.hid_banco_areia_a edgv.hid_barragem_a edgv.hid_barragem_l edgv.hid_barragem_p edgv.hid_canal_a edgv.hid_canal_l edgv.hid_comporta_l edgv.hid_comporta_p edgv.hid_corredeira_a edgv.hid_corredeira_l edgv.hid_corredeira_p edgv.hid_dique_a edgv.hid_dique_l edgv.hid_dique_p edgv.hid_fonte_dagua_p edgv.hid_foz_maritima_a edgv.hid_foz_maritima_l edgv.hid_foz_maritima_p edgv.hid_ilha_a edgv.hid_ilha_p edgv.hid_massa_dagua_a edgv.hid_quebramar_molhe_a edgv.hid_quebramar_molhe_l edgv.hid_queda_dagua_l edgv.hid_queda_dagua_p edgv.hid_recife_a edgv.hid_recife_p edgv.hid_rocha_em_agua_a edgv.hid_rocha_em_agua_p edgv.hid_sumidouro_vertedouro_p edgv.hid_terreno_sujeito_inundacao_a edgv.hid_trecho_drenagem_l edgv.hid_vala_a edgv.hid_vala_l edgv.laz_arquibancada_a edgv.laz_arquibancada_l edgv.laz_campo_quadra_a edgv.laz_campo_quadra_p edgv.laz_piscina_a edgv.laz_pista_competicao_a edgv.laz_pista_competicao_l edgv.laz_pista_competicao_p edgv.laz_ruina_a edgv.laz_ruina_p edgv.laz_sitio_arqueologico_a edgv.laz_sitio_arqueologico_p edgv.lml_area_densamente_edificada_a edgv.lml_area_pub_militar_a edgv.lml_area_urbana_isolada_a edgv.lml_distrito_a edgv.lml_municipio_a edgv.lml_nome_local_p edgv.lml_pais_a edgv.lml_posic_geo_localidade_p edgv.lml_terra_indigena_a edgv.lml_terra_publica_a edgv.lml_unidade_conservacao_a edgv.lml_unidade_federacao_a edgv.lml_unidade_protecao_integral_a edgv.lml_unidade_uso_sustentavel_a edgv.pto_marco_de_limite_p edgv.pto_pto_est_med_fenomenos_p edgv.pto_pto_geod_topo_controle_p edgv.pto_pto_ref_geod_topo_p edgv.rel_alteracao_fisiografica_antropica_a edgv.rel_alteracao_fisiografica_antropica_l edgv.rel_alteracao_fisiografica_antropica_p edgv.rel_aterro_a edgv.rel_aterro_l edgv.rel_aterro_p edgv.rel_corte_a edgv.rel_corte_l edgv.rel_corte_p edgv.rel_curva_batimetrica_l edgv.rel_curva_nivel_l edgv.rel_dolina_a edgv.rel_dolina_p edgv.rel_duna_a edgv.rel_duna_l edgv.rel_duna_p edgv.rel_elemento_fisiografico_natural_a edgv.rel_elemento_fisiografico_natural_l edgv.rel_elemento_fisiografico_natural_p edgv.rel_gruta_caverna_l edgv.rel_gruta_caverna_p edgv.rel_pico_p edgv.rel_ponto_cotado_altimetrico_p edgv.rel_ponto_cotado_batimetrico_p edgv.rel_rocha_a edgv.rel_rocha_l edgv.rel_rocha_p edgv.rel_terreno_exposto_a edgv.rod_trecho_rodoviario_a edgv.rod_trecho_rodoviario_l edgv.snb_barragem_calcadao_a edgv.snb_dep_abast_agua_a edgv.snb_dep_abast_agua_p edgv.tra_caminho_aereo_l edgv.tra_caminho_carrocavel_l edgv.tra_entroncamento_pto_p edgv.tra_funicular_l edgv.tra_passagem_elevada_viaduto_a edgv.tra_passagem_elevada_viaduto_l edgv.tra_passagem_elevada_viaduto_p edgv.tra_passagem_nivel_p edgv.tra_patio_a edgv.tra_ponte_a edgv.tra_ponte_l edgv.tra_ponte_p edgv.tra_travessia_l edgv.tra_travessia_p edgv.tra_travessia_pedestre_a edgv.tra_travessia_pedestre_l edgv.tra_travessia_pedestre_p edgv.tra_trilha_picada_l edgv.tra_tunel_a edgv.tra_tunel_l edgv.tra_tunel_p edgv.veg_brejo_pantano_a edgv.veg_caatinga_a edgv.veg_campinarana_a edgv.veg_campo_a edgv.veg_cerrado_a edgv.veg_floresta_a edgv.veg_mangue_a edgv.veg_reflorestamento_a edgv.veg_veg_area_contato_a edgv.veg_veg_cultivada_a edgv.veg_veg_restinga_a edgv.ver_arvore_isolada_p edgv.ver_jardim_a

Readers:
- POSTGIS_1: POSTGIS from $(SourceDataset_POSTGIS_2)
- POSTGIS_3: POSTGIS from $(SourceDataset_POSTGIS)

Writers:
- POSTGIS_2: POSTGIS to $(DestDataset_POSTGIS)

Note: trd
aaa010 (reader POSTGIS_1)
    attributes: id serial, ppo int2, nfn varchar(255), nfi varchar(255), nam varchar(255), fun int2, mzn int2, acc int2, ccn varchar(255), sdv varchar(255), sdp varchar(255), srt int2, txt varchar(255), uid varchar(255), cab int2, sdt int2, trs int2, tipo int2, wd1 float4, hwt int2, categoria varchar(255), wid float4, tos int2, mes int2, rac int2, vsp int2, obs varchar(255), rra int2, cat int2, fmm int2,
      zva float4, wtc int2, sta int2, rkf int2, mi varchar(255), rta int2, ttc int2, na2 varchar(255), ffn int2, rrc int2, vgt int2, wle int2, veg int2, boc int2, hyp int2, caa int2, cod int2, pby int2, bsc int2, pwc int2, sfs int2, fpt int2, ohb float4, rst int2, cda int2, tre int2, rgc int2, ray int2, nst int2, len float4,
      dmb float4, eet int2, tuc int2, wst int2, smc int2, wft int2, fic int2, ord int2, azc int2, iko varchar(255), ssc int2, bot int2, rel int2, bac int2, sep int2, slt int2, bloco varchar(255), crm int2, aoo float4, opc int2, afa int2, swt int2, ltn int4, fhc int2, prm int2, cns int2, rsa int2, con int2, fuc int2, frt int2,
      cct int2, scc int2, haf int2, tid int2, lfa int2, voi varchar(255), rwc int2, suc int2, rir int2, fac int2, loc int2, cra int2, dmt float4, csp int2, nos int4, gnc int2, ffp int2, gaw float4, mcc int2, wcc int2, hgt float4, corrigido int2, atc int2, ppc int2, hct int2, sdo float4
    -> Deaggregator
    -> _All_
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> GeometryFilter
GeometryFilter
    BREAK_AGG = No
    GEOM_PORT_NAMES = Point Line Area
    POINT -> PythonCaller_TRD_EDGV30
    LINE -> PythonCaller_TRD_EDGV30
    AREA -> PythonCaller_TRD_EDGV30
Note: mapeamento
PythonCaller_TRD_EDGV30
    NEW_ATTRIBUTES = CLASS_NOT_FOUND
    PYTHONSOURCE:
      import fme
      import fmeobjects
      import copy
      import sys
      import os
      import json

      class FeatureProcessor(object):
          def __init__(self):
              self.mappingDict = self.buildFileDict(FME_MacroValues['JsonMapeamento'])
              self.mappingType = FME_MacroValues['direcao']

          def buildFileDict(self, mappingPath):
              with open(mappingPath, 'r', encoding='utf-8') as file:
                  mapDict = json.loads(file.read())
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          if feature.getAttribute(attr) == 'f':
                              featDict[attr] = 'False'
                          elif feature.getAttribute(attr) == 't':
                              featDict[attr] = 'True'
                          else:
                              featDict[attr] = feature.getAttribute(attr)
                      else:
                          featDict[attr] = None
              if feature.performFunction('@GeometryType()') == 'fme_polygon' or feature.performFunction('@GeometryType()') == 'fme_donut':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              else:
                   featDict["INVALID_GEOM"] = True
              return featDict

          def evaluateExpression(self, featDict, expression):
              if not expression["nome_atributo"] in featDict:
                  return False
              if expression["valor"] is None or expression["valor"] == "":
                  return featDict[expression["nome_atributo"]] is None or featDict[expression["nome_atributo"]] == ""
              else:
                  return u"{0}".format(featDict[expression["nome_atributo"]]) == u"{0}".format(expression["valor"])

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "A=>B":
                  key_attr_origin = "attr_A"
                  key_attr_destiny = "attr_B"
                  key_value_origin = "valor_A"
                  key_value_destiny = "valor_B"
                  key_default = "atributos_default_B"
                  key_filter = "filtro_A"
                  key_class_origin = "classe_A"
                  key_class_destiny = "classe_B"
                  key_group_origin = "tupla_A"
                  key_group_destiny = "tupla_B"
                  key_affix_origin = "afixo_geom_A"
                  key_affix_destiny = "afixo_geom_B"
                  key_schema_origin = "schema_A"
                  key_schema_destiny = "schema_B"
                  key_class_affix_origin = "com_afixo_geom_A"
                  key_class_affix_destiny = "com_afixo_geom_B"
                  key_class_schema_origin = "com_schema_A"
                  key_class_schema_destiny = "com_schema_B"
                  key_agregar = "agregar_geom_A"
              else:
                  key_attr_origin = "attr_B"
                  key_attr_destiny = "attr_A"
                  key_value_origin = "valor_B"
                  key_value_destiny = "valor_A"
                  key_default = "atributos_default_A"
                  key_filter = "filtro_B"
                  key_class_origin = "classe_B"
                  key_class_destiny = "classe_A"
                  key_group_origin = "tupla_B"
                  key_group_destiny = "tupla_A"
                  key_affix_origin = "afixo_geom_B"
                  key_affix_destiny = "afixo_geom_A"
                  key_schema_origin = "schema_B"
                  key_schema_destiny = "schema_A"
                  key_class_affix_origin = "com_afixo_geom_B"
                  key_class_affix_destiny = "com_afixo_geom_A"
                  key_class_schema_origin = "com_schema_B"
                  key_class_schema_destiny = "com_schema_A"
                  key_agregar = "agregar_geom_B"

              featDict["fme_feature_type_original"] = featDict["fme_feature_type"]

              if key_schema_origin in self.mappingDict and self.mappingDict[key_schema_origin]:
                  featDict["fme_feature_type"] = featDict["fme_feature_type"][len(self.mappingDict[key_schema_origin])+1:]

              featDict["fme_feature_type_sem_schema"] = featDict["fme_feature_type"]

              if key_affix_origin in self.mappingDict and 'tipo' in self.mappingDict[key_affix_origin] and self.mappingDict[key_affix_origin]['tipo'] == 'sufixo':
                  featDict["fme_feature_type"] = featDict["fme_feature_type"][:-len(self.mappingDict[key_affix_origin][featDict["$GEOM_TYPE"]])]
                  featDict["fme_feature_type_sem_afixo"] = featDict["fme_feature_type_original"][:-len(self.mappingDict[key_affix_origin][featDict["$GEOM_TYPE"]])]

              if key_affix_origin in self.mappingDict and 'tipo' in self.mappingDict[key_affix_origin] and self.mappingDict[key_affix_origin]['tipo'] == 'prefixo':
                  featDict["fme_feature_type"] = featDict["fme_feature_type"][len(self.mappingDict[key_affix_origin][featDict["$GEOM_TYPE"]]):]
                  featDict["fme_feature_type_sem_afixo"] = featDict["fme_feature_type_original"][len(self.mappingDict[key_affix_origin][featDict["$GEOM_TYPE"]]):]

              should_map = False
              for classmap in self.mappingDict['mapeamento_classes']:
                  if "sentido" not in classmap or ("sentido" in classmap and classmap["sentido"] == self.mappingType):
                      if key_class_affix_origin in classmap and classmap[key_class_affix_origin] and key_class_schema_origin in classmap and classmap[key_class_schema_origin]:
                          class_name = featDict["fme_feature_type_original"]
                      elif key_class_affix_origin in classmap and classmap[key_class_affix_origin]:
                          class_name = featDict["fme_feature_type_sem_schema"]
                      elif key_class_schema_origin in classmap and classmap[key_class_schema_origin]:
                          class_name = featDict["fme_feature_type_sem_afixo"]
                      else:
                           class_name = featDict["fme_feature_type"]

                      if classmap[key_class_origin] == class_name:
                          if key_filter in classmap:
                              if not self.evaluateFilter(featDict, classmap[key_filter]):
                                  continue
                          should_map = True
              if not should_map:
                  featDict["CLASS_NOT_FOUND"] = True
                  return featDict

              mappedFeat = copy.deepcopy(featDict)

              if key_default in self.mappingDict:
                  for default in self.mappingDict[key_default]:
                      mappedFeat[default["nome_atributo"]] = default["valor"]

              if 'mapeamento_atributos' in self.mappingDict:
                  for attmap in self.mappingDict['mapeamento_atributos']:
                      if attmap[key_attr_origin] in mappedFeat:
                          mappedFeat[attmap[key_attr_destiny]] = featDict[attmap[key_attr_origin]]
                          if "traducao" in attmap:
                              for valuemap in attmap["traducao"]:
                                  if u"{0}".format(valuemap[key_value_origin]) == u"{0}".format(featDict[attmap[key_attr_origin]]) and ("sentido" not in valuemap or ("sentido" in valuemap and valuemap["sentido"] == self.mappingType)):
                                      mappedFeat[attmap[key_attr_destiny]] = valuemap[key_value_destiny]

              if "mapeamento_multiplo" in self.mappingDict:
                  for attmap in self.mappingDict['mapeamento_multiplo']:
                      if "sentido" not in attmap or ("sentido" in attmap and attmap["sentido"] == self.mappingType):
                          if all([self.evaluateExpression(featDict, condition) for condition in attmap[key_group_origin]]):
                              for valuemap in attmap[key_group_destiny]:
                                  if "concatenar" in valuemap and valuemap["concatenar"] and valuemap["nome_atributo"] in mappedFeat and mappedFeat[valuemap["nome_atributo"]]:
                                      mappedFeat[valuemap["nome_atributo"]] = mappedFeat[valuemap["nome_atributo"]] + ' | ' + valuemap["valor"]
                                  else:
                                      mappedFeat[valuemap["nome_atributo"]] = valuemap["valor"]

              if 'mapeamento_classes' in self.mappingDict:
                  for classmap in self.mappingDict['mapeamento_classes']:
                      if "sentido" not in classmap or ("sentido" in classmap and classmap["sentido"] == self.mappingType):
                          if key_class_affix_origin in classmap and classmap[key_class_affix_origin] and key_class_schema_origin in classmap and classmap[key_class_schema_origin]:
                              class_name = featDict["fme_feature_type_original"]
                          elif key_class_affix_origin in classmap and classmap[key_class_affix_origin]:
                              class_name = featDict["fme_feature_type_sem_schema"]
                          elif key_class_schema_origin in classmap and classmap[key_class_schema_origin]:
                              class_name = featDict["fme_feature_type_sem_afixo"]
                          else:
                              class_name = featDict["fme_feature_type"]

                          if classmap[key_class_origin] == class_name:
                              if key_filter in classmap:
                                  if not self.evaluateFilter(featDict, classmap[key_filter]):
                                      continue

                              mappedFeat["fme_feature_type"] = classmap[key_class_destiny]

                              if key_class_affix_destiny in classmap and classmap[key_class_affix_destiny]:
                                  pass
                              elif key_affix_destiny in self.mappingDict and 'tipo' in self.mappingDict[key_affix_destiny]:
                                  if self.mappingDict[key_affix_destiny]['tipo'] == 'sufixo':
                                      mappedFeat["fme_feature_type"] = mappedFeat["fme_feature_type"] + self.mappingDict[key_affix_destiny][featDict["$GEOM_TYPE"]]

                                  if self.mappingDict[key_affix_destiny]['tipo'] == 'prefixo':
                                      mappedFeat["fme_feature_type"] = self.mappingDict[key_affix_destiny][featDict["$GEOM_TYPE"]] + mappedFeat["fme_feature_type"]

                              if key_class_schema_destiny in classmap and classmap[key_class_schema_destiny]:
                                  pass
                              elif key_schema_destiny in self.mappingDict and self.mappingDict[key_schema_destiny]:
                                  mappedFeat["fme_feature_type"] = self.mappingDict[key_schema_destiny] + '.' + mappedFeat["fme_feature_type"]


                              if key_default in classmap:
                                  for default in classmap[key_default]:
                                      mappedFeat[default["nome_atributo"]] = default["valor"]

                              if "mapeamento_atributos" in classmap:
                                  for attmap in classmap['mapeamento_atributos']:
                                      if attmap[key_attr_origin] in featDict:
                                          if attmap[key_attr_destiny] not in mappedFeat:
                                              mappedFeat[attmap[key_attr_destiny]] = featDict[attmap[key_attr_origin]]
                                          if "traducao" in attmap:
                                              for valuemap in attmap["traducao"]:
                                                  if u"{0}".format(valuemap[key_value_origin]) == u"{0}".format(featDict[attmap[key_attr_origin]]) and ("sentido" not in valuemap or ("sentido" in valuemap and valuemap["sentido"] == self.mappingType)):
                                                      mappedFeat[attmap[key_attr_destiny]] = valuemap[key_value_destiny]

                              if "mapeamento_multiplo" in classmap:
                                  for attmap in classmap['mapeamento_multiplo']:
                                      if "sentido" not in attmap or ("sentido" in attmap and attmap["sentido"] == self.mappingType):
                                          if all([self.evaluateExpression(featDict, condition) for condition in attmap[key_group_origin]]):
                                              for valuemap in attmap[key_group_destiny]:
                                                  if "concatenar" in valuemap and valuemap["concatenar"] and valuemap["nome_atributo"] in mappedFeat and mappedFeat[valuemap["nome_atributo"]]:
                                                      mappedFeat[valuemap["nome_atributo"]] = mappedFeat[valuemap["nome_atributo"]] + ' | ' + valuemap["valor"]
                                                  else:
                                                      mappedFeat[valuemap["nome_atributo"]] = valuemap["valor"]

                              if key_agregar in classmap:
                                  mappedFeat["AGGREGATE_GEOM"] = classmap[key_agregar]
                              elif key_agregar in self.mappingDict:
                                  mappedFeat["AGGREGATE_GEOM"] = self.mappingDict[key_agregar]

                              break

              return mappedFeat

          def mapDictToFeature(self, feat, featDict):
              for attr, value in featDict.items():
                  if value == 'True':
                      feat.setAttribute(attr, 1)
                  elif value == 'False':
                      feat.setAttribute(attr, 0)
                  elif value or value == 0:
                      feat.setAttribute(attr, u'{0}'.format(value))
                  else:
                      feat.setAttributeNullWithType(attr,0)
              if "AGGREGATE_GEOM" in featDict and featDict["AGGREGATE_GEOM"]:
                  feat.buildAggregateFeat([feat])
              return feat

          def input(self,feature):
              if feature.performFunction('@GeometryType()') == 'fme_aggregate':
                  features = feature.splitAggregate(True)
              else:
                  features = [feature]
              for simple_feature in features:
                  feat = self.buildFeatureDict(simple_feature)
                  if "INVALID_GEOM" in feat and feat["INVALID_GEOM"]:
                      simple_feature.setAttribute("INVALID_GEOM", u'True')
                      self.pyoutput(simple_feature)
                      continue

                  outputFeatDict = self.convertFeature(feat)
                  if "CLASS_NOT_FOUND" in outputFeatDict and not outputFeatDict["CLASS_NOT_FOUND"]:
                      simple_feature.setAttribute("CLASS_NOT_FOUND", u'True')
                      self.pyoutput(simple_feature)
                  else:
                      outputFeature = self.mapDictToFeature(simple_feature, outputFeatDict)
                      self.pyoutput(outputFeature)

          def close(self):
              pass
    PYTHONSYMBOL = FeatureProcessor
    -> Tester_4
Note: Teste de mapeamento
Tester_4
    BOOL_OP = OR
    TEST_CLAUSE = TEST @Value(CLASS_NOT_FOUND) = True
    TEST_MODE = TEST
    PASSED -> AttributeCreator
    PASSED -> DuplicateFilter
    FAILED -> Deaggregator_2
DuplicateFilter
    INPUT_ORDERED_CHOICE = No
    KEYATTR = fme_feature_type
    UNIQUE -> DuplicateFilter_Unique
    DUPLICATE -> DuplicateFilter_Duplicate
DuplicateFilter_Unique: Inspector
DuplicateFilter_Duplicate: Inspector
AttributeCreator [off]
    ATTR_TABLE:
      SET_TO descricao = @Value(fme_feature_type)
      SET_TO corrigido = false
    -> GeometryFilter_2
GeometryFilter_2
    FILTER_MODE = SIMPLE
    FILTER_MULTI = FILTER_TYPES]"Point Line Area"]FME_CONTROLLER_QUERY_FILE]]FME_CONTROLLER_CHOICE]Simple
    Point -> AttributeCreator_2
    Curve -> AttributeCreator_3
    Area -> AttributeCreator_4
AttributeCreator_2
    ATTR_TABLE = SET_TO fme_feature_type (buffer) = edgv.aux_revisao_p
    -> UUIDGenerator
AttributeCreator_3
    ATTR_TABLE = SET_TO fme_feature_type (buffer) = edgv.aux_revisao_l
    -> UUIDGenerator
AttributeCreator_4
    ATTR_TABLE = SET_TO fme_feature_type (buffer) = edgv.aux_revisao_a
    -> UUIDGenerator
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> UUIDGenerator
UUIDGenerator
    UUID_ATTR = id
    -> Aggregator
Aggregator
    ACCUM_ATTRS_NAME = Use Attributes From One Feature
    AGGREGATE_TYPE = Homogeneous Collection (If Possible)
    GROUP_BY = id
    MODE = Geometry - Assemble One Level
    SEP = ,
    AGGREGATE -> Table1 (writer POSTGIS_2)
Table1 (writer POSTGIS_2)
_All_: Inspector
aer_pista_ponto_pouso_a (reader POSTGIS_3)
    attributes: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
