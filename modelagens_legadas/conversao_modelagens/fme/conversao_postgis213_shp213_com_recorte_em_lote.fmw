FME workspace conversao_postgis213_shp213_com_recorte_em_lote.fmw

Parameters:
- SourceDataset_POSTGIS = ci_baraodesaoborja_25k_4674_edgv30   # Database PG
- HOST_POSTGIS = 10.25.163.12   # Host PG
- PORT_POSTGIS = 5432   # Port PG
- USER_NAME_POSTGIS = postgres   # Username PG
- PASSWORD_POSTGIS =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   # Password PG
- direcao = ida   # Direção do mapeamento
- JsonMapeamento = C:\Diniz\modelagens\conversao_modelagens\arquivos_mapeamento\conversao_pg-edgv-300_shp-edgv-300.json   # Arquivo de mapeamento
- SourceDataset_ESRISHAPE =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   # SHPs de referência
- DestDataset_ESRISHAPE = W:\Produtos_2024\2024_CIBSB\CDGV   # Pasta destino dos SHP
- reprojetar = Sim   # Reprojetar para 4674?
- ESPG = 31981
- SourceDataset_SHAPEFILE = C:\Users\diniz\Downloads\moldura.shp   # Source Esri Shapefile(s)
- FEATURE_TYPES_2 =
- DEST = EPSG:31981   # Destination Coordinate System

Readers:
- SHAPEFILE_1: SHAPEFILE from $(SourceDataset_SHAPEFILE)

Note: Molduras
generalizacao_17rcmec_50k (reader SHAPEFILE_1)
    attributes: id long, mi varchar(10), inom varchar(29), escala varchar(254), area_supri varchar(7)
    -> Reprojector
Reprojector
    DEST = $(DEST)
    INTERPOLATION_TYPE_NAME = Nearest Neighbor
    RASTER_CELL_SIZE = Preserve Cells
    RASTER_TOLERANCE = 0.0
    REPROJECTED -> GeometryExtractor
GeometryExtractor
    ATTR = _geometry
    KIND_LONG = OGC Well Known Text
    OGCVERSION = 1.2
    OGC_WKT_PRECISION_DISPLAY = 64-bit
    REMOVE_GEOMETRY = No
    -> AttributeCreator
AttributeCreator
    ATTR_TABLE = SET_TO ewkt = SRID=$(ESPG);@Value(_geometry)
    -> WorkspaceRunner
WorkspaceRunner
    BLOCKING = Yes
    WORKSPACE_FILE = $(FME_MF_DIR)conversao_postgis213_shp213_com_recorte.fmw
    WORKSPACE_PARAMETERS = SourceDataset_POSTGIS,$(SourceDataset_POSTGIS),HOST_POSTGIS,$(HOST_POSTGIS),PORT_POSTGIS,$(PORT_POSTGIS),USER_NAME_POSTGIS,$(USER_NAME_POSTGIS),PASSWORD_POSTGIS,$(PASSWORD_POSTGIS),direcao,$(direcao),JsonMapeamento,$(JsonMapeamento),SourceDataset_ESRISHAPE,$(SourceDataset_ESRISHAPE),DestDataset_ESRISHAPE,$(DestDataset_ESRISHAPE)/@Value(mi),dbarea_where_clause,@Value(ewkt),reprojetar,$(reprojetar)
    SUCCEEDED -> WorkspaceRunner_Succeeded
    FAILED -> WorkspaceRunner_Failed
    SUMMARY -> WorkspaceRunner_Summary
WorkspaceRunner_Succeeded: Inspector
WorkspaceRunner_Failed: Inspector
WorkspaceRunner_Summary: Inspector
