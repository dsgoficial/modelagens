FME workspace conversao_postgis213_shp213.fmw

Parameters:
- DestDataset_ESRISHAPE =
- FEATURE_TYPES =
- FEATURE_TYPES_2 =
- FME_USER_PARAM_PRIVATE_GRP =
- HOST_POSTGIS =
- JsonMapeamento =
- PASSWORD_POSTGIS =
- PORT_POSTGIS =
- SourceDataset_ESRISHAPE =
- SourceDataset_POSTGIS =
- USER_NAME_POSTGIS =
- direcao =

Readers:
- POSTGIS_1: POSTGIS from $(SourceDataset_POSTGIS)
- ESRISHAPE_1: ESRISHAPE from $(SourceDataset_ESRISHAPE)

Writers:
- ESRISHAPE_2: ESRISHAPE to $(DestDataset_ESRISHAPE)

Note: PostGIS EDGV 2.1.3
adm_area_pub_civil_a (reader POSTGIS_1)
    attributes: id serial, geometriaaproximada int2, tipoedifmil int2, nascente int2, namaximomaximorum int4, obs varchar(255), mattransp int2, tipocemiterio int2, coletiva int2, tipoprodutoresiduo int2, codigootto int4, tipotorre int2, relacionado int2, historicomodificacao varchar(255), classificacaoporte int2, rede int2, tipopostofisc int2, orgaoenteresp varchar(255), potenciafiscalizada float4, perimetrooficial float4, canteirodivisorio int2, tipoobst int2, vaovertical float4, latitude varchar(255), tipoptoestmed int2, tipoptoenergia int2, tipotunel int2, profundidademedia float4, nrdutos int4, denso int2,
      classe varchar(255), pesosuportmaximo float4, especie int2, tiposinal int2, tipotravessia int2, procextracao int2, codigoestacao varchar(255), tipolimpol int2, tipooutlimofic int2, regime int2, nomeabrev varchar(255), referencialaltim int2, tipoedifrod int2, codtrechoferrov varchar(255), tipoestgerad int2, revestimento int2, obssituacao varchar(255), situacaoespacial int2, tipoclassecnae int2, tipomarcolim int2, larguramedia float4, matconstr int2, tipoilha int2, emarruamento int2, dentrodepoligono int2, formaextracao int2, sigla varchar(255), destinadoa int2, caladomax float4, tiporecife int2,
      extensao float4, tipotrechoferrov int2, causa int2, coincidecomdentrode int2, classificacao varchar(255), isolada int2, velocidademedcorrente float4, situacaofisica int2, tipocapital int2, codprojeto varchar(255), espessuradap float4, tipooutunidprot int2, tipoedifagropec int2, destinacaofundeadouro int2, cotacomprovada int2, nrfaixas int4, tipofontedagua int2, especiepredominante int2, arranjofases varchar(255), espessalgas int2, tipodivisaocnae int2, tipogrutacaverna int2, altura float4, nrpistas int4, tipolimareaesp int2, posicaorelativa int2, identificador varchar(255), codestacao varchar(255), tipodepgeral int2, tipolimintramun int2,
      tipousoedif int2, tiporesiduo int2, codponto varchar(255), atolegal varchar(255), periodicidadeinunda varchar(255), tipotravessiaped int2, caladomaxseca float4, destenergelet int2, homologacao int2, datavisita varchar(255), alturalamina float4, tipoassociado int2, cultivopredominante int2, espacamentoindividuos float4, tipoatracad int2, altitudeortometrica float4, gabhorizsup float4, tipocombustivel int2, trafego int2, largura float4, gabvertsup float4, usopista int2, nrlinhas int2, nome varchar(255), extensaotrecho float4, areaoficial varchar(255), modaluso int2, tipopista int2, tipocampo int2, administracao int2,
      tipoaglomrurisol int2, setor int2, posicaopista int2, anocriacao varchar(255), areaoficialha float4, geracao int2, tipousocaminhoaer int2, tipopassagviad int2, tipolavoura int2, alturaestimada float4, compartilhado int2, nivelotto int4, tiporocha int2, tipoponte int2, tipoexposicao int2, codigohidreletrica varchar(255), atividade int2, indice int2, tipotrechoduto int2, navegabilidade int2, tipomacchav int2, numcircuitos int4, tipocaminhoaereo int2, tipocondutor int2, tipoptocontrole int2, situacaoemagua int2, tipotrechocomunic int2, qualidagua int2, tipoedifrelig int2, tipoextmin int2,
      tipodepabast int2, tipolimoper int2, datasituacaojuridica date, tipoedifturist int2, ensino int2, salinidade int2, tipomassadagua int2, materializado int2, tipounidusosust int2, multimodal int2, tipoedifcivil int2, tipoedifaero int2, jurisdicao int2, tipoterrexp int2, emduto int2, tipotrechorod int2, situacaoagua int2, tipoequipagropec int2, funcaoedifmetroferrov int2, outrarefalt varchar(255), vaolivrehoriz float4, tipocampoquadra int2, cargasuportmaxima float4, sistemageodesico int2, cota int4, eletrificada int2, nivelatencao int2, tipoalterantrop int2, tipoplataforma int2, descricao varchar(255),
      unidadevolume int2, mi varchar(255), tensaoeletrica float4, posicaoreledific int2, residuo int2, namaximooperacional int4, alturamediaindividuos float4, tiposumvert int2, finalidade int2, tipoedifabast int2, tiposecaocnae int2, materialpredominante int2, usoprincipal int2, modalidade int2, operacional int2, tipopostopol int2, religiao varchar(255), tipoareausocomun int2, proximidade int2, tipoptorefgeodtopo int2, grupoetnico varchar(255), escala varchar(255), valorvolume float4, situacaocosta int2, geocodigo varchar(255), terreno int2, outrarefplan varchar(255), tipoediflazer int2, causaexposicao int2, chamine int2,
      tipotrechomassa int2, tipoquebramolhe int2, profundidade int4, referencialgrav int2, eixoprincipal int2, tipocerr int2, tipoedifcomunic int2, tipoconteudo int2, potenciaoutorgada float4, nometi varchar(255), tipoareaumida int2, tipobanco int2, ocorrenciaem int2, tipopocomina int2, caracteristicafloresta int2, combrenovavel int2, tipoelemnat int2, tipodelimfis int2, tratamento int2, concessionaria varchar(255), capaccarga float4, anodereferencia int4, codtrechorodov varchar(255), alturamediamargem float4, codiso3166 varchar(255), motivodescontinuidade int2, tipobrejopantano int2, tipoedifsaneam int2, orgresp varchar(255), tipoentroncamento int2,
      tipoedifenergia int2, construcao int2, inom varchar(255), tipomaqtermica int2, denominacaoassociada int2, volumeutil int4, situamare int2, tipoedifcomercserv int2, tipodepsaneam int2, bitola int2, tipolimmassa int2, tipoqueda int2, fixa int2, desnivel float4, situacaomarco int2, tipounidprotinteg int2, calado float4, situacaojuridica int2, ovgd int2, tipolocalcrit int2, longitude varchar(255), depressao int2, tiporef int2, antropizada int2, tipoedifport int2
    -> PythonCaller_2
Note: mapeamento
PythonCaller_2
    NEW_ATTRIBUTES = CLASS_NOT_FOUND
    PYTHONSOURCE:
      import fme
      import fmeobjects
      import copy
      import sys
      import os
      import json

      class FeatureProcessor(object):
          def __init__(self):
              self.mappingDict = self.buildFileDict(FME_MacroValues['JsonMapeamento'])
              self.mappingType = FME_MacroValues['direcao']

          def buildFileDict(self, mappingPath):
              with open(mappingPath, 'r', encoding='utf-8') as file:
                  mapDict = json.loads(file.read())
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          if feature.getAttribute(attr) == 'f':
                              featDict[attr] = 'False'
                          elif feature.getAttribute(attr) == 't':
                              featDict[attr] = 'True'
                          else:
                              featDict[attr] = feature.getAttribute(attr)
                      else:
                          featDict[attr] = None
              if feature.performFunction('@GeometryType()') == 'fme_polygon' or feature.performFunction('@GeometryType()') == 'fme_donut':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              else:
                   featDict["INVALID_GEOM"] = True
              return featDict

          def evaluateExpression(self, featDict, expression):
              if not expression["nome_atributo"] in featDict:
                  return False
              if expression["valor"] is None or expression["valor"] == "":
                  return featDict[expression["nome_atributo"]] is None or featDict[expression["nome_atributo"]] == ""
              else:
                  return u"{0}".format(featDict[expression["nome_atributo"]]) == u"{0}".format(expression["valor"])

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "ida":
                  key_attr_origin = "attr_ida"
                  key_attr_destiny = "attr_volta"
                  key_value_origin = "valor_ida"
                  key_value_destiny = "valor_volta"
                  key_default = "atributos_default_ida"
                  key_filter = "filtro_ida"
                  key_class_origin = "classe_ida"
                  key_class_destiny = "classe_volta"
                  key_group_origin = "tupla_ida"
                  key_group_destiny = "tupla_volta"
                  key_affix_origin = "afixo_geom_ida"
                  key_affix_destiny = "afixo_geom_volta"
                  key_schema_origin = "schema_ida"
                  key_schema_destiny = "schema_volta"
                  key_class_affix_origin = "com_afixo_geom_ida"
                  key_class_affix_destiny = "com_afixo_geom_volta"
                  key_class_schema_origin = "com_schema_ida"
                  key_class_schema_destiny = "com_schema_volta"
                  key_agregar = "agregar_geom_ida"
              else:
                  key_attr_origin = "attr_volta"
                  key_attr_destiny = "attr_ida"
                  key_value_origin = "valor_volta"
                  key_value_destiny = "valor_ida"
                  key_default = "atributos_default_volta"
                  key_filter = "filtro_volta"
                  key_class_origin = "classe_volta"
                  key_class_destiny = "classe_ida"
                  key_group_origin = "tupla_volta"
                  key_group_destiny = "tupla_ida"
                  key_affix_origin = "afixo_geom_volta"
                  key_affix_destiny = "afixo_geom_ida"
                  key_schema_origin = "schema_volta"
                  key_schema_destiny = "schema_ida"
                  key_class_affix_origin = "com_afixo_geom_volta"
                  key_class_affix_destiny = "com_afixo_geom_ida"
                  key_class_schema_origin = "com_schema_volta"
                  key_class_schema_destiny = "com_schema_ida"
                  key_agregar = "agregar_geom_volta"

              featDict["fme_feature_type_original"] = featDict["fme_feature_type"]

              if key_schema_origin in self.mappingDict and self.mappingDict[key_schema_origin]:
                  featDict["fme_feature_type"] = featDict["fme_feature_type"][len(self.mappingDict[key_schema_origin])+1:]

              featDict["fme_feature_type_sem_schema"] = featDict["fme_feature_type"]

              if key_affix_origin in self.mappingDict and 'tipo' in self.mappingDict[key_affix_origin] and self.mappingDict[key_affix_origin]['tipo'] == 'sufixo':
                  featDict["fme_feature_type"] = featDict["fme_feature_type"][:-len(self.mappingDict[key_affix_origin][featDict["$GEOM_TYPE"]])]
                  featDict["fme_feature_type_sem_afixo"] = featDict["fme_feature_type_original"][:-len(self.mappingDict[key_affix_origin][featDict["$GEOM_TYPE"]])]

              if key_affix_origin in self.mappingDict and 'tipo' in self.mappingDict[key_affix_origin] and self.mappingDict[key_affix_origin]['tipo'] == 'prefixo':
                  featDict["fme_feature_type"] = featDict["fme_feature_type"][len(self.mappingDict[key_affix_origin][featDict["$GEOM_TYPE"]]):]
                  featDict["fme_feature_type_sem_afixo"] = featDict["fme_feature_type_original"][len(self.mappingDict[key_affix_origin][featDict["$GEOM_TYPE"]]):]

              should_map = False
              for classmap in self.mappingDict['mapeamento_classes']:
                  if "sentido" not in classmap or ("sentido" in classmap and classmap["sentido"] == self.mappingType):
                      if key_class_affix_origin in classmap and classmap[key_class_affix_origin] and key_class_schema_origin in classmap and classmap[key_class_schema_origin]:
                          class_name = featDict["fme_feature_type_original"]
                      elif key_class_affix_origin in classmap and classmap[key_class_affix_origin]:
                          class_name = featDict["fme_feature_type_sem_schema"]
                      elif key_class_schema_origin in classmap and classmap[key_class_schema_origin]:
                          class_name = featDict["fme_feature_type_sem_afixo"]
                      else:
                           class_name = featDict["fme_feature_type"]

                      if classmap[key_class_origin] == class_name:
                          if key_filter in classmap:
                              if not self.evaluateFilter(featDict, classmap[key_filter]):
                                  continue
                          should_map = True
              if not should_map:
                  featDict["CLASS_NOT_FOUND"] = True
                  return featDict

              mappedFeat = copy.deepcopy(featDict)

              if key_default in self.mappingDict:
                  for default in self.mappingDict[key_default]:
                      mappedFeat[default["nome_atributo"]] = default["valor"]

              if 'mapeamento_atributos' in self.mappingDict:
                  for attmap in self.mappingDict['mapeamento_atributos']:
                      if attmap[key_attr_origin] in mappedFeat:
                          mappedFeat[attmap[key_attr_destiny]] = featDict[attmap[key_attr_origin]]
                          if "traducao" in attmap:
                              for valuemap in attmap["traducao"]:
                                  if u"{0}".format(valuemap[key_value_origin]) == u"{0}".format(featDict[attmap[key_attr_origin]]) and ("sentido" not in valuemap or ("sentido" in valuemap and valuemap["sentido"] == self.mappingType)):
                                      mappedFeat[attmap[key_attr_destiny]] = valuemap[key_value_destiny]

              if "mapeamento_multiplo" in self.mappingDict:
                  for attmap in self.mappingDict['mapeamento_multiplo']:
                      if "sentido" not in attmap or ("sentido" in attmap and attmap["sentido"] == self.mappingType):
                          if all([self.evaluateExpression(featDict, condition) for condition in attmap[key_group_origin]]):
                              for valuemap in attmap[key_group_destiny]:
                                  if "concatenar" in valuemap and valuemap["concatenar"] and valuemap["nome_atributo"] in mappedFeat and mappedFeat[valuemap["nome_atributo"]]:
                                      mappedFeat[valuemap["nome_atributo"]] = mappedFeat[valuemap["nome_atributo"]] + ' | ' + valuemap["valor"]
                                  else:
                                      mappedFeat[valuemap["nome_atributo"]] = valuemap["valor"]

              if 'mapeamento_classes' in self.mappingDict:
                  for classmap in self.mappingDict['mapeamento_classes']:
                      if "sentido" not in classmap or ("sentido" in classmap and classmap["sentido"] == self.mappingType):
                          if key_class_affix_origin in classmap and classmap[key_class_affix_origin] and key_class_schema_origin in classmap and classmap[key_class_schema_origin]:
                              class_name = featDict["fme_feature_type_original"]
                          elif key_class_affix_origin in classmap and classmap[key_class_affix_origin]:
                              class_name = featDict["fme_feature_type_sem_schema"]
                          elif key_class_schema_origin in classmap and classmap[key_class_schema_origin]:
                              class_name = featDict["fme_feature_type_sem_afixo"]
                          else:
                              class_name = featDict["fme_feature_type"]

                          if classmap[key_class_origin] == class_name:
                              if key_filter in classmap:
                                  if not self.evaluateFilter(featDict, classmap[key_filter]):
                                      continue

                              mappedFeat["fme_feature_type"] = classmap[key_class_destiny]

                              if key_class_affix_destiny in classmap and classmap[key_class_affix_destiny]:
                                  pass
                              elif key_affix_destiny in self.mappingDict and 'tipo' in self.mappingDict[key_affix_destiny]:
                                  if self.mappingDict[key_affix_destiny]['tipo'] == 'sufixo':
                                      mappedFeat["fme_feature_type"] = mappedFeat["fme_feature_type"] + self.mappingDict[key_affix_destiny][featDict["$GEOM_TYPE"]]

                                  if self.mappingDict[key_affix_destiny]['tipo'] == 'prefixo':
                                      mappedFeat["fme_feature_type"] = self.mappingDict[key_affix_destiny][featDict["$GEOM_TYPE"]] + mappedFeat["fme_feature_type"]

                              if key_class_schema_destiny in classmap and classmap[key_class_schema_destiny]:
                                  pass
                              elif key_schema_destiny in self.mappingDict and self.mappingDict[key_schema_destiny]:
                                  mappedFeat["fme_feature_type"] = self.mappingDict[key_schema_destiny] + '.' + mappedFeat["fme_feature_type"]


                              if key_default in classmap:
                                  for default in classmap[key_default]:
                                      mappedFeat[default["nome_atributo"]] = default["valor"]

                              if "mapeamento_atributos" in classmap:
                                  for attmap in classmap['mapeamento_atributos']:
                                      if attmap[key_attr_origin] in featDict:
                                          if attmap[key_attr_destiny] not in mappedFeat:
                                              mappedFeat[attmap[key_attr_destiny]] = featDict[attmap[key_attr_origin]]
                                          if "traducao" in attmap:
                                              for valuemap in attmap["traducao"]:
                                                  if u"{0}".format(valuemap[key_value_origin]) == u"{0}".format(featDict[attmap[key_attr_origin]]) and ("sentido" not in valuemap or ("sentido" in valuemap and valuemap["sentido"] == self.mappingType)):
                                                      mappedFeat[attmap[key_attr_destiny]] = valuemap[key_value_destiny]

                              if "mapeamento_multiplo" in classmap:
                                  for attmap in classmap['mapeamento_multiplo']:
                                      if "sentido" not in attmap or ("sentido" in attmap and attmap["sentido"] == self.mappingType):
                                          if all([self.evaluateExpression(featDict, condition) for condition in attmap[key_group_origin]]):
                                              for valuemap in attmap[key_group_destiny]:
                                                  if "concatenar" in valuemap and valuemap["concatenar"] and valuemap["nome_atributo"] in mappedFeat and mappedFeat[valuemap["nome_atributo"]]:
                                                      mappedFeat[valuemap["nome_atributo"]] = mappedFeat[valuemap["nome_atributo"]] + ' | ' + valuemap["valor"]
                                                  else:
                                                      mappedFeat[valuemap["nome_atributo"]] = valuemap["valor"]

                              if key_agregar in classmap:
                                  mappedFeat["AGGREGATE_GEOM"] = classmap[key_agregar]
                              elif key_agregar in self.mappingDict:
                                  mappedFeat["AGGREGATE_GEOM"] = self.mappingDict[key_agregar]

                              break

              return mappedFeat

          def mapDictToFeature(self, feat, featDict):
              for attr, value in featDict.items():
                  if value or value == 0:
                      feat.setAttribute(attr, u'{0}'.format(value))
                  else:
                      feat.setAttributeNullWithType(attr,0)
              if "AGGREGATE_GEOM" in featDict and featDict["AGGREGATE_GEOM"]:
                  feat.buildAggregateFeat([feat])
              return feat

          def input(self,feature):
              if feature.performFunction('@GeometryType()') == 'fme_aggregate':
                  features = feature.splitAggregate(True)
              else:
                  features = [feature]
              for simple_feature in features:
                  feat = self.buildFeatureDict(simple_feature)
                  if "INVALID_GEOM" in feat and not feat["INVALID_GEOM"]:
                      simple_feature.setAttribute("INVALID_GEOM", u'True')
                      self.pyoutput(simple_feature)
                      continue

                  outputFeatDict = self.convertFeature(feat)
                  if "CLASS_NOT_FOUND" in outputFeatDict and not outputFeatDict["CLASS_NOT_FOUND"]:
                      simple_feature.setAttribute("CLASS_NOT_FOUND", u'True')
                      self.pyoutput(simple_feature)
                  else:
                      outputFeature = self.mapDictToFeature(simple_feature, outputFeatDict)
                      self.pyoutput(outputFeature)

          def close(self):
              pass
    PYTHONSYMBOL = FeatureProcessor
    -> Tester_4
Note: Teste de mapeamento
Tester_4
    BOOL_OP = OR
    COMPOSITE_TEST = 1
    TEST_CLAUSE = TEST @Value(CLASS_NOT_FOUND) = True
    TEST_MODE = TEST
    PASSED -> CLASSE_NAO_ENCONTRADA
    FAILED -> Shapefile1 (writer ESRISHAPE_2)
CLASSE_NAO_ENCONTRADA: Inspector
Shapefile1 (writer ESRISHAPE_2)
Note: SHP EDGV 2.1.3 / utilizado como recurso pro mapeamento dinâmico
ADM_Area_Pub_Civil_A (reader ESRISHAPE_1) [off]
    attributes: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
