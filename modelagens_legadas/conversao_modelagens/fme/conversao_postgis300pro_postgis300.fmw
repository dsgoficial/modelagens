FME workspace conversao_postgis300pro_postgis300.fmw

Parameters:
- JsonMapeamento = C:\Diniz\modelagens\modelagens_legadas\conversao_modelagens\conversao_pg-edgv-300_pg-edgv-300pro.json   # Arquivo de mapeamento
- SourceDataset_POSTGIS = decex_esacosaae_50k_4674_edgv30pro   # Database origem (Topo)
- HOST_POSTGIS = 10.25.163.12   # Host Origem
- PORT_POSTGIS = 5432   # Porta Origem
- USER_NAME_POSTGIS = postgres   # Username Origem
- PASSWORD_POSTGIS =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   # Password Origem
- DestDataset_POSTGIS = decex_esacosaae_50k_4674_edgv30   # Database destino
- HOST_POSTGIS_2 = 10.25.163.12   # Host Destino
- PORT_POSTGIS_2 = 5432   # Porta Destino
- USER_NAME_POSTGIS_2 = postgres   # Username Destino
- PASSWORD_POSTGIS_2 =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   # Password Destino
- FEATURE_TYPES = edgv.aer_pista_ponto_pouso_a edgv.aer_pista_ponto_pouso_l edgv.aer_pista_ponto_pouso_p edgv.aux_moldura_a edgv.aux_obstaculo_vertical_p edgv.aux_revisao_a edgv.aux_revisao_l edgv.aux_revisao_p edgv.cbge_area_agropec_ext_vegetal_pesca_a edgv.cbge_area_construida_a edgv.cbge_area_de_propriedade_particular_a edgv.cbge_area_duto_a edgv.cbge_area_habitacional_a edgv.cbge_area_uso_especifico_a edgv.cbge_assentamento_precario_a edgv.cbge_canteiro_central_a edgv.cbge_canteiro_central_l edgv.cbge_cemiterio_a edgv.cbge_cemiterio_p edgv.cbge_delimitacao_fisica_l edgv.cbge_deposito_geral_a edgv.cbge_deposito_geral_p edgv.cbge_entroncamento_area_a edgv.cbge_espelho_dagua_a edgv.cbge_estacionamento_a edgv.cbge_largo_a edgv.cbge_passeio_a edgv.cbge_passeio_l edgv.cbge_poste_p edgv.cbge_praca_a edgv.cbge_quadra_a edgv.cbge_retorno_l edgv.cbge_retorno_p edgv.cbge_trecho_arruamento_a edgv.cbge_trecho_arruamento_l edgv.dut_galeria_bueiro_l edgv.dut_galeria_bueiro_p edgv.dut_trecho_duto_l edgv.eco_equip_agropec_a edgv.eco_equip_agropec_l edgv.eco_equip_agropec_p edgv.eco_ext_mineral_a edgv.eco_ext_mineral_p edgv.eco_plataforma_a edgv.eco_plataforma_p edgv.edf_banheiro_publico_a edgv.edf_banheiro_publico_p edgv.edf_edif_abast_agua_a edgv.edf_edif_abast_agua_p edgv.edf_edif_agropec_ext_vegetal_pesca_a edgv.edf_edif_agropec_ext_vegetal_pesca_p edgv.edf_edif_comerc_serv_a edgv.edf_edif_comerc_serv_p edgv.edf_edif_comunic_a edgv.edf_edif_comunic_p edgv.edf_edif_constr_aeroportuaria_a edgv.edf_edif_constr_aeroportuaria_p edgv.edf_edif_constr_est_med_fen_a edgv.edf_edif_constr_est_med_fen_p edgv.edf_edif_constr_lazer_a edgv.edf_edif_constr_lazer_p edgv.edf_edif_constr_portuaria_a edgv.edf_edif_constr_portuaria_p edgv.edf_edif_constr_turistica_a edgv.edf_edif_constr_turistica_p edgv.edf_edif_desenv_social_a edgv.edf_edif_desenv_social_p edgv.edf_edif_energia_a edgv.edf_edif_energia_p edgv.edf_edif_ensino_a edgv.edf_edif_ensino_p edgv.edf_edif_ext_mineral_a edgv.edf_edif_ext_mineral_p edgv.edf_edif_industrial_a edgv.edf_edif_industrial_p edgv.edf_edif_metro_ferroviaria_a edgv.edf_edif_metro_ferroviaria_p edgv.edf_edif_policia_a edgv.edf_edif_policia_p edgv.edf_edif_pub_civil_a edgv.edf_edif_pub_civil_p edgv.edf_edif_pub_militar_a edgv.edf_edif_pub_militar_p edgv.edf_edif_religiosa_a edgv.edf_edif_religiosa_p edgv.edf_edif_residencial_a edgv.edf_edif_residencial_p edgv.edf_edif_rodoviaria_a edgv.edf_edif_rodoviaria_p edgv.edf_edif_saneamento_a edgv.edf_edif_saneamento_p edgv.edf_edif_saude_a edgv.edf_edif_saude_p edgv.edf_edificacao_a edgv.edf_edificacao_p edgv.edf_hab_indigena_a edgv.edf_hab_indigena_p edgv.edf_posto_combustivel_a edgv.edf_posto_combustivel_p edgv.edf_posto_fiscal_a edgv.edf_posto_fiscal_p edgv.edf_posto_guarda_municipal_a edgv.edf_posto_guarda_municipal_p edgv.edf_posto_policia_militar_a edgv.edf_posto_policia_militar_p edgv.edf_posto_policia_rod_federal_a edgv.edf_posto_policia_rod_federal_p edgv.edf_representacao_diplomatica_a edgv.edf_representacao_diplomatica_p edgv.emu_acesso_a edgv.emu_acesso_l edgv.emu_acesso_p edgv.emu_ciclovia_l edgv.emu_elevador_a edgv.emu_elevador_l edgv.emu_elevador_p edgv.emu_escadaria_a edgv.emu_escadaria_l edgv.emu_escadaria_p edgv.emu_poste_sinalizacao_p edgv.emu_rampa_a edgv.emu_rampa_l edgv.emu_rampa_p edgv.enc_aerogerador_p edgv.enc_antena_comunic_p edgv.enc_casa_de_forca_p edgv.enc_central_geradora_eolica_a edgv.enc_central_geradora_eolica_p edgv.enc_est_gerad_energia_eletrica_a edgv.enc_est_gerad_energia_eletrica_p edgv.enc_grupo_transformadores_a edgv.enc_grupo_transformadores_p edgv.enc_hidreletrica_a edgv.enc_hidreletrica_l edgv.enc_hidreletrica_p edgv.enc_subest_transm_distrib_energia_eletrica_a edgv.enc_subest_transm_distrib_energia_eletrica_p edgv.enc_termeletrica_a edgv.enc_termeletrica_p edgv.enc_torre_comunic_p edgv.enc_torre_energia_p edgv.enc_trecho_comunic_l edgv.enc_trecho_energia_l edgv.enc_zona_linhas_energia_comunicacao_a edgv.fer_cremalheira_l edgv.fer_cremalheira_p edgv.fer_girador_ferroviario_p edgv.fer_trecho_ferroviario_l edgv.hdv_atracadouro_terminal_a edgv.hdv_atracadouro_terminal_l edgv.hdv_atracadouro_terminal_p edgv.hdv_eclusa_a edgv.hdv_eclusa_l edgv.hdv_eclusa_p edgv.hdv_fundeadouro_a edgv.hdv_fundeadouro_p edgv.hdv_obstaculo_navegacao_a edgv.hdv_obstaculo_navegacao_l edgv.hdv_obstaculo_navegacao_p edgv.hdv_sinalizacao_p edgv.hdv_trecho_hidroviario_l edgv.hid_area_umida_a edgv.hid_banco_areia_a edgv.hid_barragem_a edgv.hid_barragem_l edgv.hid_barragem_p edgv.hid_canal_a edgv.hid_canal_l edgv.hid_comporta_l edgv.hid_comporta_p edgv.hid_corredeira_a edgv.hid_corredeira_l edgv.hid_corredeira_p edgv.hid_dique_a edgv.hid_dique_l edgv.hid_dique_p edgv.hid_fonte_dagua_p edgv.hid_foz_maritima_l edgv.hid_foz_maritima_p edgv.hid_ilha_a edgv.hid_ilha_p edgv.hid_massa_dagua_a edgv.hid_quebramar_molhe_a edgv.hid_quebramar_molhe_l edgv.hid_queda_dagua_l edgv.hid_queda_dagua_p edgv.hid_recife_a edgv.hid_recife_p edgv.hid_rocha_em_agua_a edgv.hid_rocha_em_agua_p edgv.hid_sumidouro_vertedouro_p edgv.hid_terreno_sujeito_inundacao_a edgv.hid_trecho_drenagem_l edgv.hid_vala_a edgv.hid_vala_l edgv.laz_arquibancada_a edgv.laz_arquibancada_l edgv.laz_campo_quadra_a edgv.laz_campo_quadra_p edgv.laz_piscina_a edgv.laz_pista_competicao_a edgv.laz_pista_competicao_l edgv.laz_pista_competicao_p edgv.laz_ruina_a edgv.laz_ruina_p edgv.laz_sitio_arqueologico_a edgv.laz_sitio_arqueologico_p edgv.lml_area_densamente_edificada_a edgv.lml_area_pub_militar_a edgv.lml_area_urbana_isolada_a edgv.lml_distrito_a edgv.lml_municipio_a edgv.lml_nome_local_p edgv.lml_pais_a edgv.lml_posic_geo_localidade_p edgv.lml_terra_indigena_a edgv.lml_terra_publica_a edgv.lml_unidade_conservacao_a edgv.lml_unidade_federacao_a edgv.lml_unidade_protecao_integral_a edgv.lml_unidade_uso_sustentavel_a edgv.pto_marco_de_limite_p edgv.pto_pto_est_med_fenomenos_p edgv.pto_pto_geod_topo_controle_p edgv.pto_pto_ref_geod_topo_p edgv.rel_alteracao_fisiografica_antropica_a edgv.rel_alteracao_fisiografica_antropica_l edgv.rel_alteracao_fisiografica_antropica_p edgv.rel_aterro_a edgv.rel_aterro_l edgv.rel_aterro_p edgv.rel_corte_a edgv.rel_corte_l edgv.rel_corte_p edgv.rel_curva_batimetrica_l edgv.rel_curva_nivel_l edgv.rel_dolina_a edgv.rel_dolina_p edgv.rel_duna_a edgv.rel_duna_l edgv.rel_duna_p edgv.rel_elemento_fisiografico_natural_a edgv.rel_elemento_fisiografico_natural_l edgv.rel_elemento_fisiografico_natural_p edgv.rel_gruta_caverna_l edgv.rel_gruta_caverna_p edgv.rel_pico_p edgv.rel_ponto_cotado_altimetrico_p edgv.rel_ponto_cotado_batimetrico_p edgv.rel_rocha_a edgv.rel_rocha_l edgv.rel_rocha_p edgv.rel_terreno_exposto_a edgv.rod_trecho_rodoviario_a edgv.rod_trecho_rodoviario_l edgv.snb_barragem_calcadao_a edgv.snb_dep_abast_agua_a edgv.snb_dep_abast_agua_p edgv.tra_caminho_aereo_l edgv.tra_caminho_carrocavel_l edgv.tra_entroncamento_pto_p edgv.tra_funicular_l edgv.tra_passagem_elevada_viaduto_a edgv.tra_passagem_elevada_viaduto_l edgv.tra_passagem_elevada_viaduto_p edgv.tra_passagem_nivel_p edgv.tra_patio_a edgv.tra_ponte_a edgv.tra_ponte_l edgv.tra_ponte_p edgv.tra_travessia_l edgv.tra_travessia_p edgv.tra_travessia_pedestre_a edgv.tra_travessia_pedestre_l edgv.tra_travessia_pedestre_p edgv.tra_trilha_picada_l edgv.tra_tunel_a edgv.tra_tunel_l edgv.tra_tunel_p edgv.veg_brejo_pantano_a edgv.veg_caatinga_a edgv.veg_campinarana_a edgv.veg_campo_a edgv.veg_cerrado_a edgv.veg_floresta_a edgv.veg_mangue_a edgv.veg_reflorestamento_a edgv.veg_veg_area_contato_a edgv.veg_veg_cultivada_a edgv.veg_veg_restinga_a edgv.ver_arvore_isolada_p edgv.ver_jardim_a edgv.enc_central_geradora_eolica_l edgv.enc_est_gerad_energia_eletrica_l edgv.hid_foz_maritima_a
- FEATURE_TYPES_2 = edgv.aux_moldura_a edgv.cobter_area_construida_a edgv.cobter_massa_dagua_a edgv.cobter_vegetacao_a edgv.constr_area_uso_especifico_a edgv.constr_deposito_a edgv.constr_deposito_p edgv.constr_edificacao_a edgv.constr_edificacao_p edgv.constr_extracao_mineral_a edgv.constr_extracao_mineral_p edgv.constr_ocupacao_solo_a edgv.constr_ocupacao_solo_l edgv.constr_ocupacao_solo_p edgv.elemnat_curva_nivel_l edgv.elemnat_elemento_fisiografico_a edgv.elemnat_elemento_fisiografico_l edgv.elemnat_elemento_fisiografico_p edgv.elemnat_elemento_hidrografico_a edgv.elemnat_elemento_hidrografico_l edgv.elemnat_elemento_hidrografico_p edgv.elemnat_ilha_a edgv.elemnat_ilha_p edgv.elemnat_ponto_cotado_p edgv.elemnat_sumidouro_vertedouro_p edgv.elemnat_terreno_sujeito_inundacao_a edgv.elemnat_toponimo_fisiografico_natural_l edgv.elemnat_toponimo_fisiografico_natural_p edgv.elemnat_trecho_drenagem_l edgv.infra_alteracao_fisiografica_antropica_l edgv.infra_barragem_a edgv.infra_barragem_l edgv.infra_elemento_energia_a edgv.infra_elemento_energia_l edgv.infra_elemento_energia_p edgv.infra_elemento_infraestrutura_a edgv.infra_elemento_infraestrutura_l edgv.infra_elemento_infraestrutura_p edgv.infra_elemento_viario_l edgv.infra_elemento_viario_p edgv.infra_ferrovia_l edgv.infra_mobilidade_urbana_l edgv.infra_pista_pouso_a edgv.infra_pista_pouso_l edgv.infra_pista_pouso_p edgv.infra_travessia_hidroviaria_l edgv.infra_trecho_duto_l edgv.infra_vala_l edgv.infra_via_deslocamento_l edgv.llp_delimitacao_fisica_l edgv.llp_limite_especial_a edgv.llp_localidade_p edgv.llp_pais_a edgv.llp_ponto_controle_p edgv.llp_unidade_federacao_a
- direcao = B=>A   # Direção do mapeamento

Readers:
- POSTGIS_1: POSTGIS from $(DestDataset_POSTGIS)
- POSTGIS_2: POSTGIS from $(SourceDataset_POSTGIS)

Writers:
- POSTGIS_3: POSTGIS to $(DestDataset_POSTGIS)

aquisicao_centroide_area_construida_p (reader POSTGIS_2)
    attributes: id serial, nome varchar(255), densamente_edificada int2, assentamento_precario int2, observacao varchar(255), data_modificacao timestamptz, controle_uuid varchar(255), usuario_criacao varchar(255), usuario_atualizacao varchar(255), insumo varchar(255), data_insumo timestamptz, administracao int2, altitude_geometrica varchar(255), altitude_ortometrica varchar(255), canteiro_divisorio int2, cod_ponto varchar(255), concessionaria varchar(255), corrigido int2, cota int4, cota_comprovada int2, depressao int2, descricao varchar(255), em_arruamento int2, em_via_deslocamento int2, finalidade int2, fonte varchar(255), forma_extracao int2, geometria_aproximada int2, indice int2, inom varchar(255),
      jurisdicao int2, justificativa varchar(255), latitude varchar(255), longitude varchar(255), material_construcao int2, mi varchar(255), modal_uso int2, nr_faixas varchar(255), nr_linhas int2, nr_pistas varchar(255), orgao_responsavel varchar(255), populacao int4, posicao_pista int2, posicao_relativa int2, referencial_altim int2, referencial_grav int2, regime int2, revestimento int2, sigla varchar(255), sistema_geodesico int2, situacao_em_poligono int2, situacao_fisica int2, situacao_marco int2, subfase_id int4, sujeito_inundacao int2, tipo int2, tipo_exposicao int2, tipo_ref int2, trafego int2, uso_pista int2
    -> PythonCaller_EDGV3
Note: mapeamento
PythonCaller_EDGV3
    NEW_ATTRIBUTES = CLASS_NOT_FOUND INVALID_GEOM
    PYTHONSOURCE:
      import fme
      import fmeobjects
      import copy
      import sys
      import os
      import json

      class FeatureProcessor(object):
          def __init__(self):
              self.mappingDict = self.buildFileDict(FME_MacroValues['JsonMapeamento'])
              self.mappingType = FME_MacroValues['direcao']

          def buildFileDict(self, mappingPath):
              with open(mappingPath, 'r', encoding='utf-8') as file:
                  mapDict = json.loads(file.read())
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          if feature.getAttribute(attr) == 'f':
                              featDict[attr] = 'False'
                          elif feature.getAttribute(attr) == 't':
                              featDict[attr] = 'True'
                          else:
                              featDict[attr] = feature.getAttribute(attr)
                      else:
                          featDict[attr] = None
              if feature.performFunction('@GeometryType()') == 'fme_polygon' or feature.performFunction('@GeometryType()') == 'fme_donut':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              else:
                   featDict["INVALID_GEOM"] = True
              return featDict

          def evaluateExpression(self, featDict, expression):
              if not expression["nome_atributo"] in featDict:
                  return False
              if expression["valor"] is None or expression["valor"] == "":
                  return featDict[expression["nome_atributo"]] is None or featDict[expression["nome_atributo"]] == ""
              else:
                  return u"{0}".format(featDict[expression["nome_atributo"]]) == u"{0}".format(expression["valor"])

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "A=>B":
                  key_attr_origin = "attr_A"
                  key_attr_destiny = "attr_B"
                  key_value_origin = "valor_A"
                  key_value_destiny = "valor_B"
                  key_default = "atributos_default_B"
                  key_filter = "filtro_A"
                  key_class_origin = "classe_A"
                  key_class_destiny = "classe_B"
                  key_group_origin = "tupla_A"
                  key_group_destiny = "tupla_B"
                  key_affix_origin = "afixo_geom_A"
                  key_affix_destiny = "afixo_geom_B"
                  key_schema_origin = "schema_A"
                  key_schema_destiny = "schema_B"
                  key_class_affix_origin = "com_afixo_geom_A"
                  key_class_affix_destiny = "com_afixo_geom_B"
                  key_class_schema_origin = "com_schema_A"
                  key_class_schema_destiny = "com_schema_B"
                  key_agregar = "agregar_geom_A"
              else:
                  key_attr_origin = "attr_B"
                  key_attr_destiny = "attr_A"
                  key_value_origin = "valor_B"
                  key_value_destiny = "valor_A"
                  key_default = "atributos_default_A"
                  key_filter = "filtro_B"
                  key_class_origin = "classe_B"
                  key_class_destiny = "classe_A"
                  key_group_origin = "tupla_B"
                  key_group_destiny = "tupla_A"
                  key_affix_origin = "afixo_geom_B"
                  key_affix_destiny = "afixo_geom_A"
                  key_schema_origin = "schema_B"
                  key_schema_destiny = "schema_A"
                  key_class_affix_origin = "com_afixo_geom_B"
                  key_class_affix_destiny = "com_afixo_geom_A"
                  key_class_schema_origin = "com_schema_B"
                  key_class_schema_destiny = "com_schema_A"
                  key_agregar = "agregar_geom_B"

              featDict["fme_feature_type_original"] = featDict["fme_feature_type"]

              if key_schema_origin in self.mappingDict and self.mappingDict[key_schema_origin]:
                  featDict["fme_feature_type"] = featDict["fme_feature_type"][len(self.mappingDict[key_schema_origin])+1:]

              featDict["fme_feature_type_sem_schema"] = featDict["fme_feature_type"]

              if key_affix_origin in self.mappingDict and 'tipo' in self.mappingDict[key_affix_origin] and self.mappingDict[key_affix_origin]['tipo'] == 'sufixo':
                  featDict["fme_feature_type"] = featDict["fme_feature_type"][:-len(self.mappingDict[key_affix_origin][featDict["$GEOM_TYPE"]])]
                  featDict["fme_feature_type_sem_afixo"] = featDict["fme_feature_type_original"][:-len(self.mappingDict[key_affix_origin][featDict["$GEOM_TYPE"]])]

              if key_affix_origin in self.mappingDict and 'tipo' in self.mappingDict[key_affix_origin] and self.mappingDict[key_affix_origin]['tipo'] == 'prefixo':
                  featDict["fme_feature_type"] = featDict["fme_feature_type"][len(self.mappingDict[key_affix_origin][featDict["$GEOM_TYPE"]]):]
                  featDict["fme_feature_type_sem_afixo"] = featDict["fme_feature_type_original"][len(self.mappingDict[key_affix_origin][featDict["$GEOM_TYPE"]]):]

              should_map = False
              for classmap in self.mappingDict['mapeamento_classes']:
                  if "sentido" not in classmap or ("sentido" in classmap and classmap["sentido"] == self.mappingType):
                      if key_class_affix_origin in classmap and classmap[key_class_affix_origin] and key_class_schema_origin in classmap and classmap[key_class_schema_origin]:
                          class_name = featDict["fme_feature_type_original"]
                      elif key_class_affix_origin in classmap and classmap[key_class_affix_origin]:
                          class_name = featDict["fme_feature_type_sem_schema"]
                      elif key_class_schema_origin in classmap and classmap[key_class_schema_origin]:
                          class_name = featDict["fme_feature_type_sem_afixo"]
                      else:
                           class_name = featDict["fme_feature_type"]

                      if classmap[key_class_origin] == class_name:
                          if key_filter in classmap:
                              if not self.evaluateFilter(featDict, classmap[key_filter]):
                                  continue
                          should_map = True
              if not should_map:
                  featDict["CLASS_NOT_FOUND"] = True
                  return featDict

              mappedFeat = copy.deepcopy(featDict)

              if key_default in self.mappingDict:
                  for default in self.mappingDict[key_default]:
                      mappedFeat[default["nome_atributo"]] = default["valor"]

              if 'mapeamento_atributos' in self.mappingDict:
                  for attmap in self.mappingDict['mapeamento_atributos']:
                      if attmap[key_attr_origin] in mappedFeat:
                          mappedFeat[attmap[key_attr_destiny]] = featDict[attmap[key_attr_origin]]
                          if "traducao" in attmap:
                              for valuemap in attmap["traducao"]:
                                  if u"{0}".format(valuemap[key_value_origin]) == u"{0}".format(featDict[attmap[key_attr_origin]]) and ("sentido" not in valuemap or ("sentido" in valuemap and valuemap["sentido"] == self.mappingType)):
                                      mappedFeat[attmap[key_attr_destiny]] = valuemap[key_value_destiny]

              if "mapeamento_multiplo" in self.mappingDict:
                  for attmap in self.mappingDict['mapeamento_multiplo']:
                      if "sentido" not in attmap or ("sentido" in attmap and attmap["sentido"] == self.mappingType):
                          if all([self.evaluateExpression(featDict, condition) for condition in attmap[key_group_origin]]):
                              for valuemap in attmap[key_group_destiny]:
                                  if "concatenar" in valuemap and valuemap["concatenar"] and valuemap["nome_atributo"] in mappedFeat and mappedFeat[valuemap["nome_atributo"]]:
                                      mappedFeat[valuemap["nome_atributo"]] = mappedFeat[valuemap["nome_atributo"]] + ' | ' + valuemap["valor"]
                                  else:
                                      mappedFeat[valuemap["nome_atributo"]] = valuemap["valor"]

              if 'mapeamento_classes' in self.mappingDict:
                  for classmap in self.mappingDict['mapeamento_classes']:
                      if "sentido" not in classmap or ("sentido" in classmap and classmap["sentido"] == self.mappingType):
                          if key_class_affix_origin in classmap and classmap[key_class_affix_origin] and key_class_schema_origin in classmap and classmap[key_class_schema_origin]:
                              class_name = featDict["fme_feature_type_original"]
                          elif key_class_affix_origin in classmap and classmap[key_class_affix_origin]:
                              class_name = featDict["fme_feature_type_sem_schema"]
                          elif key_class_schema_origin in classmap and classmap[key_class_schema_origin]:
                              class_name = featDict["fme_feature_type_sem_afixo"]
                          else:
                              class_name = featDict["fme_feature_type"]

                          if classmap[key_class_origin] == class_name:
                              if key_filter in classmap:
                                  if not self.evaluateFilter(featDict, classmap[key_filter]):
                                      continue

                              mappedFeat["fme_feature_type"] = classmap[key_class_destiny]

                              if key_class_affix_destiny in classmap and classmap[key_class_affix_destiny]:
                                  pass
                              elif key_affix_destiny in self.mappingDict and 'tipo' in self.mappingDict[key_affix_destiny]:
                                  if self.mappingDict[key_affix_destiny]['tipo'] == 'sufixo':
                                      mappedFeat["fme_feature_type"] = mappedFeat["fme_feature_type"] + self.mappingDict[key_affix_destiny][featDict["$GEOM_TYPE"]]

                                  if self.mappingDict[key_affix_destiny]['tipo'] == 'prefixo':
                                      mappedFeat["fme_feature_type"] = self.mappingDict[key_affix_destiny][featDict["$GEOM_TYPE"]] + mappedFeat["fme_feature_type"]

                              if key_class_schema_destiny in classmap and classmap[key_class_schema_destiny]:
                                  pass
                              elif key_schema_destiny in self.mappingDict and self.mappingDict[key_schema_destiny]:
                                  mappedFeat["fme_feature_type"] = self.mappingDict[key_schema_destiny] + '.' + mappedFeat["fme_feature_type"]


                              if key_default in classmap:
                                  for default in classmap[key_default]:
                                      mappedFeat[default["nome_atributo"]] = default["valor"]

                              if "mapeamento_atributos" in classmap:
                                  for attmap in classmap['mapeamento_atributos']:
                                      if attmap[key_attr_origin] in featDict:
                                          if attmap[key_attr_destiny] not in mappedFeat:
                                              mappedFeat[attmap[key_attr_destiny]] = featDict[attmap[key_attr_origin]]
                                          if "traducao" in attmap:
                                              for valuemap in attmap["traducao"]:
                                                  if u"{0}".format(valuemap[key_value_origin]) == u"{0}".format(featDict[attmap[key_attr_origin]]) and ("sentido" not in valuemap or ("sentido" in valuemap and valuemap["sentido"] == self.mappingType)):
                                                      mappedFeat[attmap[key_attr_destiny]] = valuemap[key_value_destiny]

                              if "mapeamento_multiplo" in classmap:
                                  for attmap in classmap['mapeamento_multiplo']:
                                      if "sentido" not in attmap or ("sentido" in attmap and attmap["sentido"] == self.mappingType):
                                          if all([self.evaluateExpression(featDict, condition) for condition in attmap[key_group_origin]]):
                                              for valuemap in attmap[key_group_destiny]:
                                                  if "concatenar" in valuemap and valuemap["concatenar"] and valuemap["nome_atributo"] in mappedFeat and mappedFeat[valuemap["nome_atributo"]]:
                                                      mappedFeat[valuemap["nome_atributo"]] = mappedFeat[valuemap["nome_atributo"]] + ' | ' + valuemap["valor"]
                                                  else:
                                                      mappedFeat[valuemap["nome_atributo"]] = valuemap["valor"]

                              if key_agregar in classmap:
                                  mappedFeat["AGGREGATE_GEOM"] = classmap[key_agregar]
                              elif key_agregar in self.mappingDict:
                                  mappedFeat["AGGREGATE_GEOM"] = self.mappingDict[key_agregar]

                              break

              return mappedFeat

          def mapDictToFeature(self, feat, featDict):
              for attr, value in featDict.items():
                  if value == 'True':
                      feat.setAttribute(attr, 1)
                  elif value == 'False':
                      feat.setAttribute(attr, 0)
                  elif value or value == 0:
                      feat.setAttribute(attr, u'{0}'.format(value))
                  else:
                      feat.setAttributeNullWithType(attr,0)
              if "AGGREGATE_GEOM" in featDict and featDict["AGGREGATE_GEOM"]:
                  feat.buildAggregateFeat([feat])
              return feat

          def input(self,feature):
              if feature.performFunction('@GeometryType()') == 'fme_aggregate':
                  features = feature.splitAggregate(True)
              else:
                  features = [feature]
              for simple_feature in features:
                  feat = self.buildFeatureDict(simple_feature)
                  if "INVALID_GEOM" in feat and feat["INVALID_GEOM"]:
                      simple_feature.setAttribute("INVALID_GEOM", u'True')
                      self.pyoutput(simple_feature)
                      continue

                  outputFeatDict = self.convertFeature(feat)
                  if "CLASS_NOT_FOUND" in outputFeatDict and not outputFeatDict["CLASS_NOT_FOUND"]:
                      simple_feature.setAttribute("CLASS_NOT_FOUND", u'True')
                      self.pyoutput(simple_feature)
                  else:
                      outputFeature = self.mapDictToFeature(simple_feature, outputFeatDict)
                      self.pyoutput(outputFeature)

          def close(self):
              pass
    PYTHONSYMBOL = FeatureProcessor
    -> Tester_2
Note: Teste de invalid geom
Tester_2
    BOOL_OP = OR
    TEST_CLAUSE = TEST @Value(INVALID_GEOM) = True
    TEST_MODE = TEST
    PASSED -> Tester_2_Passed
    FAILED -> Tester_4
Tester_2_Passed: Inspector
Note: Teste de mapeamento
Tester_4
    BOOL_OP = OR
    TEST_CLAUSE = TEST @Value(CLASS_NOT_FOUND) = True
    TEST_MODE = TEST
    PASSED -> DuplicateFilter
    FAILED -> Reprojector
DuplicateFilter
    INPUT_ORDERED_CHOICE = No
    KEYATTR = fme_feature_type
    UNIQUE -> CLASS_NOT_FOUND
CLASS_NOT_FOUND: Inspector
Reprojector
    DEST = EPSG:4674
    INTERPOLATION_TYPE_NAME = Nearest Neighbor
    RASTER_CELL_SIZE = Preserve Cells
    RASTER_TOLERANCE = 0.0
    REPROJECTED -> Table1 (writer POSTGIS_3)
Table1 (writer POSTGIS_3)
aer_pista_ponto_pouso_a (reader POSTGIS_1)
    attributes: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
